EMAP-MIB DEFINITIONS ::= BEGIN
                                 IMPORTS
huawei
FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                             FROM SNMPv2-TC;

DisplayString ::= TEXTUAL-CONVENTION
                                             STATUS current
                                             DESCRIPTION 
                                             "Description."
                                             SYNTAX OCTET STRING (SIZE (1..64))
                                             
                                             RowStatus ::= TEXTUAL-CONVENTION
                                             STATUS current
                                             DESCRIPTION 
                                             "Description."
                                             SYNTAX INTEGER
                                             {
                                                     active(1),
                                                     notInService(2),
                                                     notReady(3),
                                                     createAndGo(4),
                                                     createAndWait(5),
                                                     destroy(6)
                                             }
                                             
                                             DateAndTime ::= TEXTUAL-CONVENTION
                                             STATUS current
                                             DESCRIPTION 
                                             "Description."
                                             SYNTAX OCTET STRING (SIZE (8..11))
                                             
                                             RunStatus ::= TEXTUAL-CONVENTION
                                             STATUS current
                                             DESCRIPTION 
                                                     "This integer value represents running status of the system. 
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }
                                             
                                             MeasuresRange ::= TEXTUAL-CONVENTION
                                             STATUS current
                                             DESCRIPTION 
                                             "Description."
                                             SYNTAX Integer32
                                             
                                             TruthValue ::= TEXTUAL-CONVENTION
                                             STATUS current
                                             DESCRIPTION 
                                             "Description."
                                             SYNTAX INTEGER
                                             {
                                                     true(1),
                                                     false(2)
                                             }
        huaweiUtility OBJECT IDENTIFIER ::= { huawei 6 }

        hwDev OBJECT IDENTIFIER ::= { huaweiUtility 3 }

        hwSystemPara OBJECT IDENTIFIER ::= { hwDev 1 }

        hwSysIpAddr OBJECT-TYPE
            SYNTAX IpAddress
            MAX-ACCESS read-write
            STATUS current
            DESCRIPTION
                "IP address of the system.
                  It'd better not to modify this address when out-band NMS is used.
                  It will take no effect to separately configure IP address or IP address mask."
            ::= { hwSystemPara 1 }

        hwSysIpMask OBJECT-TYPE
            SYNTAX IpAddress (8..16)
            MAX-ACCESS read-write
            STATUS current
            DESCRIPTION
                "IP address mask of the system.
                  This object can take effect only when hwSysIpAddr is also set.
                "
            ::= { hwSystemPara 2 }

        hwUpgradeVerifyVersion  OBJECT-TYPE
            SYNTAX OCTET STRING (SIZE (0..63))
            MAX-ACCESS read-only
            STATUS current
            DESCRIPTION
                "/"
            ::= { hwSystemPara 31 }

        hwSlotConf OBJECT IDENTIFIER ::= { hwDev 3 }

        hwFrameTable OBJECT-TYPE
            SYNTAX SEQUENCE OF HwFrameEntry
            MAX-ACCESS not-accessible
             STATUS current
             DESCRIPTION
                "The index of this table is hwFrameTable.
                                Shelf description table that describes basic information of a shelf.
                                You can obtain the shelf information, including the shelf type,
                                number of slots, and the shelf running status, and the shelf management status."
            ::= { hwSlotConf 1 }

        hwFrameEntry OBJECT-TYPE
                        SYNTAX HwFrameEntry
            MAX-ACCESS not-accessible
             STATUS current
             DESCRIPTION
                "The index of this table is hwFrameTable.
                                Shelf description table that describes basic information of a shelf.
                                You can obtain the shelf information, including the shelf type,
                                number of slots, and the shelf running status, and the shelf management status."
            INDEX { hwFrameIndex }
            ::= { hwFrameTable 1 }

        HwFrameEntry            ::= SEQUENCE {
                hwFrameIndex
                    Unsigned32,
                hwFrameType
                    Integer32,
                hwFrameAdminStatus
                    INTEGER
            }

        hwFrameIndex OBJECT-TYPE
            SYNTAX Unsigned32
            MAX-ACCESS read-only
            STATUS current
            DESCRIPTION
                "The index of a shelf in the device.
                "
            ::= { hwFrameEntry 1 }

        hwFrameType OBJECT-TYPE
            SYNTAX Integer32
            MAX-ACCESS read-only
            STATUS current
            DESCRIPTION
                "The type of a shelf, which can be obtained from HUAWEI-TC-MIB.mib."
            ::= { hwFrameEntry 2 }

        hwFrameAdminStatus OBJECT-TYPE
            SYNTAX INTEGER
                {
                nooperation(-1),
                                disable(1),
                                enable(2),
                                reset(3),
                                test(4),
                                confirm(5),
                                delete(6),
                                batchconfirm(7),
                                bind(8)
                }
            MAX-ACCESS read-write
            STATUS current
            DESCRIPTION
                "The administration status of frame.
                                Options:
                                1. nooperation(-1) -  default state of the system
                                2. disable(1)      -  indicates that the frame administration state is disable
                                3. enable(2)       -  indicates that the frame administration state is enable
                                4. reset(3)        -  reset the shelf. If you need to reset the shelf immediately,
                                                      perform the operation only. If you need to reset the shelf after a certain period,
                                                      you also need to set hwFrameResetTimeout.
                                                      If you need to reset the control shelf, the entire system is reset;
                                                      otherwise, the control board in the specified shelf is reset
                                5. test(4)         -  test the frame
                                6. confirm(5)      -  confirm the frame
                                7. delete(6)       -  delete the frame info
                                8. batchconfirm(7) -  confirm the boards in a shelf in batches
                                9. bind(8)         -  bind ont serial number with the extended frame ID"
            ::= { hwFrameEntry 6 }

        hwSlotTable OBJECT-TYPE
            SYNTAX SEQUENCE OF HwSlotEntry
            MAX-ACCESS not-accessible
             STATUS current
             DESCRIPTION
                "The board description table, used to manage the running status of
                                boards and board information, such as description of boards,
                                daughter board quantity and board type.
                                The indexes of this table are hwFrameIndex and hwSlotIndex.
                                For the hwFrameIndex object, refer to hwFrameTable.
                                For example, 0.2 indicates that the board is in slot 2, shelf 0."
            ::= { hwSlotConf 2 }

        hwSlotEntry OBJECT-TYPE
                        SYNTAX HwSlotEntry
            MAX-ACCESS not-accessible
             STATUS current
             DESCRIPTION
                "The board description table, used to manage the running status of
                                boards and board information, such as description of boards,
                                daughter board quantity and board type.
                                The indexes of this table are hwFrameIndex and hwSlotIndex.
                                For the hwFrameIndex object, refer to hwFrameTable.
                                For example, 0.2 indicates that the board is in slot 2, shelf 0."
            INDEX { hwSlotType }
            ::= { hwSlotTable 1 }

        HwSlotEntry            ::= SEQUENCE {
                hwSlotType
                    Integer32,
                hwSlotWorkMode
                    INTEGER,
                hwSlotOperStatus 
                    INTEGER
            }

        hwSlotType OBJECT-TYPE
            SYNTAX Integer32
            MAX-ACCESS read-create
            STATUS current
            DESCRIPTION
                "Board type, which is defined in HUAWEI-TC-MIB.mib.
                                The board type supported by a slot varies. For example, a slot can be inserted with a power board only,
                                but certain slots can be inserted with voice service boards and broadband service boards.
                                When adding a board by using the hwSlotRowStatus,
                                you need to specify the board information such as board type and slot number.
                                When adding a board, you need to check whether the board can be inserted in the specified slot."
            ::= { hwSlotEntry 2 }

        hwSlotWorkMode OBJECT-TYPE
            SYNTAX INTEGER
                {
                main(1),
                                standby(2),
                                loadshare(3),
                                nullbackup(4),
                                voice(5),
                                satop(6),
                                pots(7),
                                isdn(8),
                                bonding(9),
                                retransmission(10),
                                nativetdm(11),
                                other(255)
                }
            MAX-ACCESS read-only
            STATUS current
            DESCRIPTION
                "Board working mode that describes whether the board is
                                working in main state or in standby with loadshare, nullbackup, voice, satop state.
                                Options:
                                1. main(1)                 - indicates that the active control board, supporting the get operation only
                                2. standby(2)              - indicates that the standby control board, supporting the get operation only
                                3. loadshare(3)            - indicates that the board working mode is load sharing
                                4. nullbackup(4)           - indicates that the board working mode is backup
                                5. voice(5)                - indicates to get and set the working mode of an EDT service board
                                6. satop(6)                - indicates to get and set the working mode of an EDT service board or TOPB service board
                                7. pots(7)                 - indicates to get and set the working mode of an VDM service board
                                8. isdn(8)                 - indicates to get and set the working mode of an VDM service board
                                9. bonding(9)              - indicates to get and set the working mode of an ADP service board
                                10. retransmission(10)      - indicates to get and set the working mode of an ADP service board
                                11. nativetdm(11)          - indicates to get and set the working mode of a TOPB service board
                                12. other(255)             - indicates other working mode
                                An EDT service board can be running either in voice mode, that is, voice(5), or in broadband mode, that is, satop(6).
                                Setting the working mode of the EDT service board causes board resetting.
                                An VDM service board can be running either in pots mode, that is, pots(7), or in isdn mode, that is, isdn(8).
                                Setting the working mode of the VDM service board causes board resetting.
                                Setting the board working mode may cause board resetting.
                                When you ar"
            ::= { hwSlotEntry 6 }

        hwSlotOperStatus  OBJECT-TYPE
            SYNTAX INTEGER
                {
                null(1),
                                normal(2),
                                fault(3),
                                forbidden(4),
                                autofind(5),
                                config(6),
                                offline(7),
                                abnormal(8),
                                versionerr(9),
                                autoload(10),
                                outofservice(11),
                                graceful(12),
                                shutdown(13),
                                energysavingshutdown(14),
                                hightempshutdown(15),
                                manualshutdown(16),
                                mismatch(17),
                                acoffshutdown(18)
                }
            MAX-ACCESS read-only
            STATUS current
            DESCRIPTION
                "The running status of a board.
                                Options:
                                1. null(1)                  -indicates that the board is null
                                2. normal(2)                -indicates that the board is running normally
                                3. fault(3)                 -indicates that the board is faulty but in position
                                4. forbidden(4)             -indicates that the board is in position but disabled
                                5. autofind(5)              -indicates that the board is in the autofind state. If a board is added through
                                                             hwSlotRowStatus and the board is not confirmed, the board is in the autofind state.
                                                             If a board is inserted in an idle slot, after the report of automatic registration,
                                                             the board is also in the autofind state
                                6. config(6)                -indicates that the board is in the configuration state.
                                                             After a board that is in the auto discovery.
                                                             state is confirmed, data needs to be configured on the board.
                                                             The board is in the configuration state during data configuration.
                                                             After a board is successfully configured, its status is changed from config(6)
                                                             to normal(2). If the configuration fails, the board status is changed from config(6) to fault(3)
                                7. offline(7)               -indicates that the board is faulty and is not in position
                                8. abnormal(8)              -indicates that the board is abnormal
                                9. versionerr(9)            -indicates that the board version is error
                
                                10. autoload(10)            -indicates that the board is in the auto loading state. If detecting a software update,
                                                             the board automa"
            ::= { hwSlotEntry 8 }

        hwUpgrade OBJECT IDENTIFIER ::= { hwDev 22 }

        hwUpgradeRequestID OBJECT-TYPE
            SYNTAX Integer32
            MAX-ACCESS read-write
            STATUS current
            DESCRIPTION
                "/"
            ::= { hwUpgrade 1 }

        hwUpgradeAdmin OBJECT-TYPE
            SYNTAX Integer32
            MAX-ACCESS read-write
            STATUS current
            DESCRIPTION
                "/"
            ::= { hwUpgrade 2 }

        hwUpgradeResetInterval OBJECT-TYPE
            SYNTAX Integer32
            MAX-ACCESS read-write
            STATUS current
            DESCRIPTION
                "/"
            ::= { hwUpgrade 3 }

        hwUpgradeTargetVersion OBJECT-TYPE
            SYNTAX OCTET STRING
            MAX-ACCESS read-write
            STATUS current
            DESCRIPTION
                "/"
            ::= { hwUpgrade 4 }

        hwUpgradeReserveTimeout OBJECT-TYPE
            SYNTAX Integer32
            MAX-ACCESS read-write
            STATUS current
            DESCRIPTION
                "/"
            ::= { hwUpgrade 5 }

        hwUpgradeCapability OBJECT-TYPE
            SYNTAX OCTET STRING
            MAX-ACCESS read-only
            STATUS current
            DESCRIPTION
                "/"
            ::= { hwUpgrade 8 }

        hwLoadBackup OBJECT IDENTIFIER ::= { huaweiUtility 6 }

        hwLoadBackupMon OBJECT IDENTIFIER ::= { hwLoadBackup 1 }

        hwLoadParaTable OBJECT-TYPE
            SYNTAX SEQUENCE OF HwLoadParaEntry
            MAX-ACCESS not-accessible
             STATUS current
             DESCRIPTION
                "Load parameter table, used to load various files to the host
                                through the NMS. The indexes of this table are hwFrameIndex and hwSlotIndex of the board.
                                For example, to load files to the board in slot 3 of frame 0, the index is 0.3."
            ::= { hwLoadBackupMon 1 }

        hwLoadParaEntry OBJECT-TYPE
                        SYNTAX HwLoadParaEntry
            MAX-ACCESS not-accessible
             STATUS current
             DESCRIPTION
                "Load parameter table, used to load various files to the host
                                through the NMS. The indexes of this table are hwFrameIndex and hwSlotIndex of the board.
                                For example, to load files to the board in slot 3 of frame 0, the index is 0.3."
            INDEX { hwLoadServerIpAddr }
            ::= { hwLoadParaTable 1 }

        HwLoadParaEntry            ::= SEQUENCE {
                hwLoadServerIpAddr
                    IpAddress,
                hwLoadMode
                    INTEGER,
                hwLoadFileName
                    OCTET STRING,
                hwLoadContent
                    INTEGER,
                hwLoadBoardType
                    Integer32,
                hwLoadUserName
                    OCTET STRING,
                hwLoadPassword
                    OCTET STRING,
                hwLoadRequestId
                    Integer32,
                hwLoadServerPort
                    Unsigned32
            }

        hwLoadServerIpAddr OBJECT-TYPE
            SYNTAX IpAddress
            MAX-ACCESS read-write
            STATUS current
            DESCRIPTION
                "The IP address of file server."
            ::= { hwLoadParaEntry 1 }

        hwLoadMode OBJECT-TYPE
            SYNTAX INTEGER
                {
                tftp(1),
                modem(2),
                ftp(3),
                smbLoadAnyBoards(4),
                sftp(5),
                other(255)
                }
            MAX-ACCESS read-write
            STATUS current
            DESCRIPTION
                "Load protocol.
                              Options:
                              1.tftp(1)   -indicates that the Trivial File Transfer Protocol (TFTP) is used to perform
                                           the loading through the network port. Select tftp(1) when the transmission mode
                                           of the server is configured to TFTP. When TFTP is used for the loading, you need
                                           not enter the user name (hwLoadUserName) and password (hwLoadPassword).
                              2.modem(2)  -indicates that the XMODEM protocol is used to perform the loading through
                                           the serial port. When you use the HyperTerminal of the OS to perform serial
                                           port configuration on the server, select modem(2). Loading through the serial port
                                           does not require networking and maintenance through the command line interface
                                           does not require NM software.
                              3.ftp(3)    -indicates that the File Transfer Protocol (FTP) is used to perform loading
                                           through the network port. When the transmission mode of the server is configured to FTP,
                                           select ftp(3). When FTP is used for the loading, you need to enter the user name (hwLoadUserName)
                                           and password (hwLoadPassword).
                              4.smbLoadAnyBoards(4)-smbLoadAnyBoards.
                              5.sftp(5)   -indicates that the Secure File Transfer Protocol (SFTP) is used to perform the loading through
                                           the network port. Select sftp(5) when the transmission mode of the server is configured to SFTP.
                                           When SFTP is used for the loading, you need to enter the user name (hwLoadUserName)
                                           and password (hwLoadPassword). The instructions and data are encrypted during transmission.
                              6.other(255)-other.
                              The SFTP transmission mode is recommended."
            ::= { hwLoadParaEntry 2 }

        hwLoadFileName OBJECT-TYPE
            SYNTAX OCTET STRING (SIZE (0..127))
            MAX-ACCESS read-write
            STATUS current
            DESCRIPTION
                "The name of the file to be loaded."
            ::= { hwLoadParaEntry 3 }

        hwLoadContent OBJECT-TYPE
            SYNTAX INTEGER
                {
                program(1),
                database(2),
                patch(3)
                }
            MAX-ACCESS read-write
            STATUS current
            DESCRIPTION
                "Type of the loaded file.
                                Options:
                                1.noloadcontent(-1)               -no file.
                                2.program(1)                      -program file.
                                3.database(2)                     -database file.
                                4.patch(3)                        -patch file.
                                5.shellMacro(4)                   -shell macro file.
                                6.resLocal(5)                     -local resource file.
                                7.resGeneral(6)                   -general resource file.
                                8.cpeDrive(7)                     -cpe drive.
                                9.programDatabase(8)              -database file.
                                10.programBios(9)                 -bios file.
                                11.programApp(10)                 -application program.
                                12.logicFpga(11)                  -fpga logic file.
                                13.logicCpld(12)                  -Cpld logic file.
                                14.logicPci(13)                   -pci logic file.
                                15.logicAfc(14)                   -afc logic file.
                                16.programMicroCode(15)           -micro code file.
                                17.programFirmware(16)            -application program of pinch board.
                                18.programHelp(17)                -program help file.
                                19.programDataFlow(18)            -flow file of card management point.
                                20.programBootFile(19)            -Boot program file of board.
                                21.logciPa(20)                    -Boot program file of board start.
                                22.webExp(21)                     -web exp file.
                                23.webNev(22)                     -web nev file.
                                24.webHelp(23)                    -web help file.
                                25.programBsp(24)                 -bsp program file.
                                26.verBinFile(25)                 -packet file.
                                27.configurationFile(26)          -configuration file.
                                28.configurationIni(40)           -configuration file of ini formatini.
                   "
            ::= { hwLoadParaEntry 4 }

        hwLoadBoardType OBJECT-TYPE
            SYNTAX Integer32
            MAX-ACCESS read-write
            STATUS current
            DESCRIPTION
                "The type of the board to be loaded, which is defined in HUAWEI-TC-MIB.mib."
            ::= { hwLoadParaEntry 5 }

        hwLoadUserName OBJECT-TYPE
            SYNTAX OCTET STRING (SIZE (0..31))
            MAX-ACCESS read-write
            STATUS current
            DESCRIPTION
                "The name of load user, which is required in FTP mode and SFTP mode
                                but is not required in any other modes."
            ::= { hwLoadParaEntry 8 }

        hwLoadPassword OBJECT-TYPE
            SYNTAX OCTET STRING (SIZE (0..16))
            MAX-ACCESS read-write
            STATUS current
            DESCRIPTION
                "The load user password, which is required in FTP mode and SFTP mode
                                but is not required in any other modes."
            ::= { hwLoadParaEntry 9 }

        hwLoadRequestId OBJECT-TYPE
            SYNTAX Integer32
            MAX-ACCESS read-write
            STATUS current
            DESCRIPTION
                "The loading request ID, which identifies the loading request delivered by the NMS.
                                According to the ID, you can query hwOperationInfoTable to obtain the status and
                                results of each loading operation.
                                A request ID can be any integer in the range of 0-0xFFFFFFFF,
                                but the IDs of different loading requests are not duplicate.
                                This object cannot be set independently.
                                The hwLoadRequestId value of -1 indicates there is no loading operation."
            ::= { hwLoadParaEntry 12 }

        hwLoadServerPort OBJECT-TYPE
            SYNTAX Unsigned32 (0..65535)
            MAX-ACCESS read-write
            STATUS current
            DESCRIPTION
                "Monitoring port on the SFTP server.
                                Range: 0-65535
                                Default: 22
                                The invalid value is 65535."
            ::= { hwLoadParaEntry 13 }

        hwBackupParaTable OBJECT-TYPE
            SYNTAX SEQUENCE OF HwBackupParaEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            ::= { hwLoadBackupMon 2 }

        hwBackupParaEntry OBJECT-TYPE
                        SYNTAX HwBackupParaEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            INDEX { hwBackupServerIpAddr }
            ::= { hwBackupParaTable 1 }

        HwBackupParaEntry            ::= SEQUENCE {
                hwBackupServerIpAddr
                    IpAddress,
                hwBackupMode
                    INTEGER,
                hwBackupFileName
                    OCTET STRING,
                hwBackupContent
                    INTEGER,
                hwBackupUserName
                    OCTET STRING,
                hwBackupPassword
                    OCTET STRING,
                hwBackupRequestID
                    Integer32,
                hwBackupServerPort
                    Unsigned32
            }

        hwBackupServerIpAddr OBJECT-TYPE
            SYNTAX IpAddress
            MAX-ACCESS read-write
            STATUS current
            DESCRIPTION
                "The IP address of file server."
            ::= { hwBackupParaEntry 1 }

        hwBackupMode OBJECT-TYPE
            SYNTAX INTEGER
                {
                tftp(1),
                modem(2),
                ftp(3),
                sftp(5),
                other(6)
                }
            MAX-ACCESS read-write
            STATUS current
            DESCRIPTION
                "Load protocol.
                  Options:
                  1.tftp(1)  -indicates that the backup is performed by using TFTP through the
                              network port. Select tftp(1) when the transmission mode of the server is
                              configured to TFTP.When TFTP is used in the backup, you need not enter the
                              user name and password.
                  2.modem(2) -indicates that the backup is performed by using the Xmodem serial
                              port protocol through the serial port. When you use the HyperTerminal of
                              the OS to configure the serial port on the server, select modem(2).
                              Loading through the serial port does not require networking and maintenance
                              through the command line interface does not require NM software.
                  3.ftp(3)   -indicates that the backup is performed by using FTP through the network
                              port. Select ftp when the transmission mode of the server is configured to FTP.
                              When FTP is used for file backup, you need to enter the user name and password.
                  4.sftp(5)  -indicates that the backup is performed by using SFTP through the network port.
                              Select sftp(5) when the transmission mode of the server is configured to SFTP.
                              When SFTP is used for file backup, the instructions and data are encrypted
                              during transmission.
                  5.other(6) -other.
                  The SFTP transmission mode is recommended."
            ::= { hwBackupParaEntry 2 }

        hwBackupFileName OBJECT-TYPE
            SYNTAX OCTET STRING (SIZE (0..128))
            MAX-ACCESS read-write
            STATUS current
            DESCRIPTION
                "The name of backup file."
            ::= { hwBackupParaEntry 3 }

        hwBackupContent OBJECT-TYPE
            SYNTAX INTEGER
                {
                nobackupcontent(-1),
                database(1),
                shellMacro(2),
                log(3),
                bill(4),
                alarm(5),
                configurationFile(14),
                program(15),
                reslocal(16),
                resgeneral(17),
                patch(18),
                programDatabase(19),
                programBios(20),
                programApp(21),
                logicFpga(22),
                logicCpld(23),
                logicPci(24),
                logicAfc(25),
                programMicroCode(26),
                programFireware(27),
                programDataFlow(28),
                programBootFile(29),
                logciPa(30),
                webExp(31),
                webNev(32),
                webHelp(33),
                programBsp(34),
                configurationIni(40),
                configurationEfs(41),
                configurationCli(42),
                programCurrent(45),
                programOther(46),
                bcdcInfo(47),
                license(49),
                programExtendedBios(51),
                boardinfo(60),
                extendedBootRom(61),
                defaultCfg(62),
                exception(63),
                versionDescribe(64),
                emuelabel(65),
                emuproofelabel(66),
                backboardelabel(67),
                nmscollectinfo(68),
                trapsyninfo(69),
                digitmap(70),
                h248Profile(71),
                sipProfile(72),
                elabel(73),
                sipDigitmap(74),
                iop(75),
                port(76),
                script(77),
                voice(78),
                framePnp(79),
                boardPnp(80),
                subboardPnp(81),
                resetRecord(82),
                hwStatusCollectInfo(83),
                deviceCapXml(84),
                cabinetelabel(120),
                batteryelabel(121),
                deviceCapabilityFile(122),
                powerRunData(123),
                crosstalkCouplingMatrix(131),
                vdsl2Xlin(132),
                ibmsFile(133),
                userfile(134),
                vectoring(135),
                xdslPortResetInfo(136),
                frameelabel(137),
                rootfs(138),
                uimage(139),
                initrd(140),
                atiboardelabel(141),
                boardspectrum(150)
                
                }
            MAX-ACCESS read-write
            STATUS current
            DESCRIPTION
                "Type of the backup file.
                  Options:
                  1.nobackupcontent(-1)             -no file.
                  2.database(1)                     -database file.
                  3.shellMacro(2)                   -shell macro file.
                  4.log(3)                          -log file.
                  5.bill(4)                         -bill file.
                  6.alarm(5)                        -alarm file.
                  7.configurationFile(14)           -configuration file.
                  8.program(15)                     -program file.
                  9.reslocal(16)                    -local resource file.
                  10.resgeneral(17)                 -general resource file.
                  11.patch(18)                      -patch file.
                  12.programDatabase(19)            -database file.
                  13.programBios(20)                -bios file.
                  14.programApp(21)                 -application file.
                  15.logicFpga(22)                  -fpga logic file.
                  16.logicCpld(23)                  -Cpld logic file.
                  17.logicPci(24)                   -pci logic file.
                  18.logicAfc(25)                   -afc logic file.
                  19.programMicroCode(26)           -micro-code file.
                  20.programFireware(27)            -application program of pinch board.
                  21.programDataFlow(28)            -flow file of card management point.
                  22.programBootFile(29)            -boot program file of the board start.
                  23.logciPa(30)                    -fpga logic file of the pinch board.
                  24.webExp(31)                     -web exp file.
                  25.webNev(32)                     -web nev file.
                  26.webHelp(33)                    -web help file.
                  27.programBsp(34)                 -bsp program file.
                  28.configurationIni(40)           -not supported.
                  29.configurationEfs(41)           -not supported.
                  30.configurationCli(42)           -not supported.
                  31.programCurrent(45)             -not supported.
                  32.programOther(46)               -not supported.
                  33.bcdcInfo(47)                   -bcdc description system in ini file.
                  34.license(49)                    -license file.
                  35.programExtendedBios(51)        -extended bios file.
                  36.boardinfo(60)                 "
            ::= { hwBackupParaEntry 4 }

        hwBackupUserName OBJECT-TYPE
            SYNTAX OCTET STRING (SIZE (0..40))
            MAX-ACCESS read-write
            STATUS current
            DESCRIPTION
                "The backup user name, which is required in FTP mode and SFTP mode
                  but is not required in TFTP mode.
                 "
            ::= { hwBackupParaEntry 6 }

        hwBackupPassword OBJECT-TYPE
            SYNTAX OCTET STRING (SIZE (0..40))
            MAX-ACCESS read-write
            STATUS current
            DESCRIPTION
                "The backup user password, which is required in FTP mode and SFTP mode
                  but is not required in TFTP mode."
            ::= { hwBackupParaEntry 7 }

        hwBackupRequestID OBJECT-TYPE
            SYNTAX Integer32
            MAX-ACCESS read-write
            STATUS current
            DESCRIPTION
                "The backup request ID, which identifies a backup request delivered by the NMS.
                  According to the ID, you can query hwOperationInfoTable to obtain
                  the status and results of each backup operation.
                  An backup request ID can be any integer in the range of 0-0xFFFFFFFF.
                  But, the IDs of different backup requests cannot duplicate.
                  This object cannot be set independently.
                  The hwBackupRequestID value of -1 indicates there is no backup operation."
            ::= { hwBackupParaEntry 9 }

        hwBackupServerPort OBJECT-TYPE
            SYNTAX Unsigned32 (0..65535)
            MAX-ACCESS read-write
            STATUS current
            DESCRIPTION
                "SFTP server listen port.
                  Range: 0-65535
                  Default: 22
                  The invalid value is 65535."
            ::= { hwBackupParaEntry 10 }

        hwExportFaultInfTable OBJECT-TYPE
            SYNTAX SEQUENCE OF HwExportFaultInfEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            ::= { hwLoadBackupMon 3 }

        hwExportFaultInfEntry OBJECT-TYPE
                        SYNTAX HwExportFaultInfEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            INDEX { hwGetFaultInfoExportPreStart }
            ::= { hwExportFaultInfTable 1 }

        HwExportFaultInfEntry            ::= SEQUENCE {
                hwGetFaultInfoExportPreStart
                    INTEGER,
                hwGetFaultInfoExportStatus
                    INTEGER
            }

        hwGetFaultInfoExportPreStart OBJECT-TYPE
            SYNTAX INTEGER
                {
                allowExport(0),
                msgError(1),
                busy(2),
                unkown(255)
                
                
                
                }
            MAX-ACCESS read-only
            STATUS current
            DESCRIPTION
                "Type of the backup file.
                  Options:
                allowExport(0),
                msgError(1),
                busy(2),"
            ::= { hwExportFaultInfEntry 1 }

        hwGetFaultInfoExportStatus OBJECT-TYPE
            SYNTAX INTEGER
                {
                exportSuccess(0),
                exportFailed(1),
                exportProcessing(2),
                exportIdErrror(3),
                unkown(255)
                
                }
            MAX-ACCESS read-only
            STATUS current
            DESCRIPTION
                "Type of the backup file.
                  Options:
                 exportSuccess(0),
                exportFailed(1),
                exportProcessing(2),
                exportIdErrror(3),
                unkown(255)
                "
            ::= { hwExportFaultInfEntry 2 }

        hwOperationInfo OBJECT IDENTIFIER ::= { hwLoadBackup 4 }

        hwOperationInfoTable OBJECT-TYPE
            SYNTAX SEQUENCE OF HwOperationInfoEntry
            MAX-ACCESS not-accessible
             STATUS current
             DESCRIPTION
                "Operation information table. Through this table,
                                you can query the status and results of data saving, loading,
                                backup, upgrading without service interruption, patch rollback,
                                and cloning operations on the NMS. The index of this table is hwOperationReqID.
                                hwOperationReqID is an operation request ID."
            ::= { hwOperationInfo 1 }

        hwOperationInfoEntry OBJECT-TYPE
                        SYNTAX HwOperationInfoEntry
            MAX-ACCESS not-accessible
             STATUS current
             DESCRIPTION
                "Operation information table. Through this table,
                                you can query the status and results of data saving, loading,
                                backup, upgrading without service interruption, patch rollback,
                                and cloning operations on the NMS. The index of this table is hwOperationReqID.
                                hwOperationReqID is an operation request ID."
            INDEX { hwOperationReqID }
            ::= { hwOperationInfoTable 1 }

        HwOperationInfoEntry            ::= SEQUENCE {
                hwOperationReqID
                    Integer32,
                hwOperationReqStatus
                    INTEGER,
                hwOperationProgress
                    Integer32,
                hwOperationReqErrStatus
                    Integer32
            }

        hwOperationReqID OBJECT-TYPE
            SYNTAX Integer32
            MAX-ACCESS read-only
            STATUS current
            DESCRIPTION
                "The requestID of this operation. This object together with hwOperationReqType,
                                identifies different operations of different types."
            ::= { hwOperationInfoEntry 1 }

        hwOperationReqStatus OBJECT-TYPE
            SYNTAX INTEGER
                {
                initial(1),
                datascanning(2),
                transferring(3),
                saving(4),
                success(5),
                fail(6),
                ioupgrade(11)
                
                }
            MAX-ACCESS read-only
            STATUS current
            DESCRIPTION
                "Current status of an operation request.
                                Options:
                                1.initial(1)     -indicates that the operation is in the preparation phase.
                                2.datascanning(2)-indicates that the operation is in the data collection phase.
                                3.transferring(3)-indicates that the operation is in the data transmission phase.
                                4.saving(4)      -indicates that the operation is in the data saving phase.
                                5.success(5)     -indicates that the operation is successful.
                                6.fail(6)        -indicates that the operation fails.
                                7.uninterruptedAutoUpgradeResetStandby(7)
                                 -indicates that automatic upgrade without service interruption is in the following state:
                                  the standby control board is being started after reset.
                                8.uninterruptedAutoUpgradeBatchHotBackupFirst(8)
                                 -indicates that automatic upgrade without service interruption is in the following state:
                                  the standby control board is restarted and hot backup on the host is under way.
                                9.uninterruptedAutoUpgradeSwitchOver(9)
                                 -indicates that automatic upgrade without service interruption is in the following state:
                                  the active control board switches to the standby one and is being restarted.
                               10.uninterruptedAutoUpgradeBatchHotBackupSecond(10)
                                 -indicates that automatic upgrade without service interruption is in the following state:
                                  the current standby control board is already restarted and hot backup on the host is being performed.
                               11.ioupgrade(11)   -indicates that automatic upgrade is in the following state:
                                  the upgrade of the service board.
                               12.systemreboot(12)-indicates that automatic upgrade with service interruption is in the following state:
                                  the system is rebooting.
                               13.serviceboardloading(13)--indicates that aut"
            ::= { hwOperationInfoEntry 3 }

        hwOperationProgress OBJECT-TYPE
            SYNTAX Integer32 (0..100)
            MAX-ACCESS read-only
            STATUS current
            DESCRIPTION
                "The progress of the operation.
                                Range: 0-100."
            ::= { hwOperationInfoEntry 4 }

        hwOperationReqErrStatus OBJECT-TYPE
            SYNTAX Integer32
            MAX-ACCESS read-only
            STATUS current
            DESCRIPTION
                "The error code of this operation. The returned error code is an NMS error code.
                                The value 0 means 'No error';
                                The value 6561510 means 'Failed to transfer the file';
                                The value 6561553 means 'Username or password error';
                                The value 6561620 means 'The server is unreachable';
                                The value 6561623 means 'Failed to operate the remote file';
                                The value 6561625 means 'The SSH key is incorrect';
                                The value 6561626 means 'The path does not exist';
                                The value 6561627 means 'The file does not exist'."
            ::= { hwOperationInfoEntry 5 }

        hwSiteMonitorMIB OBJECT IDENTIFIER ::= { huaweiUtility 164 }

        hwSiteMonitorMIBObjects OBJECT IDENTIFIER ::= { hwSiteMonitorMIB 1 }

        hwSiteInfo OBJECT IDENTIFIER ::= { hwSiteMonitorMIBObjects 1 }

        hwSiteSummary OBJECT IDENTIFIER ::= { hwSiteInfo 1 }

        hwSiteId OBJECT-TYPE
            SYNTAX OCTET STRING
            MAX-ACCESS read-only
            STATUS current
            DESCRIPTION
                "Site ID, default value: 000,000.Naming rule of the site device ID (six digits): 
                The first three digits indicate the device name and the last three digits indicate the serial number (SN) of the device. 
                If the last three digits are 000, it indicates a virtual device."
            ::= { hwSiteSummary 1 }

        hwSiteName OBJECT-TYPE
            SYNTAX OCTET STRING (SIZE (0..63))
            MAX-ACCESS read-write
            STATUS current
            DESCRIPTION
                "Site name, which users can configure, is used to specify a site.  Otherwise, the configured character can not be any other languages except English."
            ::= { hwSiteSummary 2 }

        hwSiteAdminAddr OBJECT-TYPE
            SYNTAX Unsigned32 (0..65535)
            MAX-ACCESS read-write
            STATUS current
            DESCRIPTION
                "Site administrant address, which users can assigned, is the unique ID of a site. 
                It is used for device management by NMS, and value range is 0 to 65535. "
            ::= { hwSiteSummary 3 }

        hwSiteDescription OBJECT-TYPE
            SYNTAX OCTET STRING (SIZE (0..63))
            MAX-ACCESS read-write
            STATUS current
            DESCRIPTION
                "Site description. It is of the character string type. It is used to describe the site information such as the site location, which users can configure.  
                Otherwise, the configured character can not be any other languages except English."
            ::= { hwSiteSummary 4 }

        hwNetIdentifier OBJECT-TYPE
            SYNTAX OCTET STRING (SIZE (0..63))
            MAX-ACCESS read-write
            STATUS current
            DESCRIPTION
                "NE ID. It is of the character string type. It is the unique ID of the site (an independent network element (NE)) on the network. 
                Otherwise, the configured character can not be any other languages except English."
            ::= { hwSiteSummary 5 }

        hwSiteIp OBJECT-TYPE
            SYNTAX OCTET STRING (SIZE (8..16))
            MAX-ACCESS read-only
            STATUS current
            DESCRIPTION
                "Site IP address, default value is 192.168.0.10. Users need to configure the site IP address."
            ::= { hwSiteSummary 6 }

        hwSiteNetmask OBJECT-TYPE
            SYNTAX OCTET STRING (SIZE (8..16))
            MAX-ACCESS read-only
            STATUS current
            DESCRIPTION
                "Site netmask, default value is 255.255.255.0. Users need to configure the site netmask."
            ::= { hwSiteSummary 7 }

        hwSiteGateway OBJECT-TYPE
            SYNTAX OCTET STRING (SIZE (8..16))
            MAX-ACCESS read-only
            STATUS current
            DESCRIPTION
                "Site gateway, default value: 192.168.0.1. Users need to configure the site gateway."
            ::= { hwSiteSummary 8 }

        hwSiteDGWorkStatus OBJECT-TYPE
            SYNTAX INTEGER
                {
                invalid(1),
                idle(2),
                running(3),
                unknown(255)
                }
            MAX-ACCESS read-only
            STATUS current
            DESCRIPTION
                "State of the diesel working state. It is an enumeration type: 
                  If the enumeration value is 1, it indicates that the diesel is in the invalid state;
                  If the enumeration value is 2, it indicates that the diesel is in the idle state;     
                  If the enumeration value is 3, it indicates that the diesel is in the running state;     
                  If the enumeration value is 255, it indicates diesel operation status unknown."
            ::= { hwSiteSummary 9 }

        hwSiteRunningStatus OBJECT-TYPE
            SYNTAX INTEGER
                {
                normal(1),
                alarm(2)
                }
            MAX-ACCESS read-only
            STATUS current
            DESCRIPTION
                "State of the site alarm state. It is an enumeration type: 
                  If the enumeration value is 1, it indicates that the site is in the normal state;
                  If the enumeration value is 2, it indicates that the site is in the alarm state."
            ::= { hwSiteSummary 10 }

        hwSiteSystemEsn OBJECT-TYPE
            SYNTAX OCTET STRING (SIZE (8..16))
            MAX-ACCESS read-only
            STATUS current
            DESCRIPTION
                "Site system ESN number, is come from the electronic tags to collect back."
            ::= { hwSiteSummary 12 }

        hwSiteTime OBJECT-TYPE
            SYNTAX OCTET STRING (SIZE (0..64))
            MAX-ACCESS read-write
            STATUS current
            DESCRIPTION
                "Set Site date and time, YYYY-MM-DD HH:MM:SS"
            ::= { hwSiteSummary 13 }

        hwSiteNetecoPrimaryServerIP OBJECT-TYPE
            SYNTAX OCTET STRING
            MAX-ACCESS read-only
            STATUS current
            DESCRIPTION
                "Neteco Primary Server IP Address"
            ::= { hwSiteSummary 14 }

        hwSiteNetecoBackupServerIP OBJECT-TYPE
            SYNTAX OCTET STRING
            MAX-ACCESS read-only
            STATUS current
            DESCRIPTION
                "Neteco Backup Server IP Address"
            ::= { hwSiteSummary 15 }

        hwSiteNetecoPortNumber OBJECT-TYPE
            SYNTAX Unsigned32
            MAX-ACCESS read-only
            STATUS current
            DESCRIPTION
                "Neteco Port Number"
            ::= { hwSiteSummary 16 }

        hwSiteMac OBJECT-TYPE
            SYNTAX OCTET STRING
            MAX-ACCESS read-only
            STATUS current
            DESCRIPTION
                "Site MAC address. Users need to configure the site MAC address."
            ::= { hwSiteSummary 17 }

        hwNMSComStatus OBJECT-TYPE
            SYNTAX INTEGER
                {
                failed(1),
                success(2),
                unknown(255)
                }
            MAX-ACCESS read-write
            STATUS current
            DESCRIPTION
                "The 3-party NMS communication status.
                It is an enumeration type:
                
                If the enumeration value is 1, it means the connection failed,
                If the enumeration value is 2, it means the connection success,,
                If the enumeration value is 255, it means the connection status is unknown,,"
            ::= { hwSiteSummary 18 }

        hwSiteSysType OBJECT-TYPE
            SYNTAX OCTET STRING (SIZE (0..100))
            MAX-ACCESS read-only
            STATUS current
            DESCRIPTION
                "System type."
            ::= { hwSiteSummary 19 }

        hwSiteAlarms OBJECT IDENTIFIER ::= { hwSiteInfo 2 }

        hwDeviceTrapOrdinalNumber OBJECT-TYPE
            SYNTAX Unsigned32 (0..65535)
            MAX-ACCESS read-write
            STATUS current
            DESCRIPTION
                "Site device event trap serial number (SN) is the unique ID of the device event trap. It is used to resend and synchronize event traps.
                Its value range is 0 to 65535. When the value exceeds the maximum value, the system automatically clears the value and numbers the alarm from 0 to 65535.   
                If the network management system (NMS) recieve the alarm number is not consequential, in such case that it notifies the SNMP agent the event trap number required.  
                So the monitor send the 100 event trap messages in maximum, after consequencial number required by NMS again. Specially, if NMS set the value to 0, the agent would clear the alarm queue automatically."
            ::= { hwSiteAlarms 1 }

        hwAlarmTrapOrdinalNumber OBJECT-TYPE
            SYNTAX Unsigned32 ( 0..4294967295)
            MAX-ACCESS read-write
            STATUS current
            DESCRIPTION
                "Site alarm serial number (SN) is the unique ID of the alarm Trap. It is used to resend and synchronize alarms. Its value range is 0 to 4294967295. When the value exceeds the maximum value, the system automatically clears the value and numbers the alarm from 0 to 4294967295.  
                If the network management system (NMS) recieve the alarm number is not consequential, in such case that it notifies the SNMP agent the alarm number required.  So the monitor send the 100 alarm messages in maximum, after consequencial number required by NMS again. Specially, if NMS set the value to 0, the agent would clear the alarm queue automatically."
            ::= { hwSiteAlarms 2 }

        hwAlarmQuantity OBJECT-TYPE
            SYNTAX Unsigned32 (0..65535)
            MAX-ACCESS read-only
            STATUS current
            DESCRIPTION
                "Alarm number in site alarm list which are support. 
                It is used for alarm list management by NMS, and value range is 0 to 65535. "
            ::= { hwSiteAlarms 3 }

        hwResendActiveAlarmTrap OBJECT-TYPE
            SYNTAX INTEGER
                {
                resend(1)
                }
            MAX-ACCESS read-write
            STATUS current
            DESCRIPTION
                "It is used for active alarm resend.If set the enumeration value is 1, it indicates resend the active alarm."
            ::= { hwSiteAlarms 4 }

        hwSiteActiveAlarmTable OBJECT-TYPE
            SYNTAX SEQUENCE OF HwSiteActiveAlarmEntry
            MAX-ACCESS not-accessible
             STATUS current
             DESCRIPTION
                ""
            ::= { hwSiteAlarms 99 }

        hwSiteActiveAlarmEntry OBJECT-TYPE
                        SYNTAX HwSiteActiveAlarmEntry
            MAX-ACCESS not-accessible
             STATUS current
             DESCRIPTION
                ""
            INDEX { hwActiveAlarmIndex }
            ::= { hwSiteActiveAlarmTable 1 }

        HwSiteActiveAlarmEntry            ::= SEQUENCE {
                hwActiveAlarmIndex
                    Integer32,
                hwActiveAlarmText
                    OCTET STRING,
                hwActiveAlarmLevel
                    INTEGER,
                hwActiveAlarmSigDesc
                    OCTET STRING,
                hwActiveAlarmTime
                    OCTET STRING,
                hwActiveAlarmRowStatus
                    RowStatus,
                hwSMUSiteName
                    OCTET STRING,
                hwSMUSiteAdminAddr
                    Unsigned32,
                hwSMUNetIdentifier
                    OCTET STRING,
                hwSMUSiteDescription
                    OCTET STRING,
                hwEquipId
                    Unsigned32,
                hwEquipName
                    OCTET STRING
            }

        hwActiveAlarmIndex OBJECT-TYPE
            SYNTAX Integer32 (1..65535)
            MAX-ACCESS read-only
            STATUS current
            DESCRIPTION
                "Site active alarm table index. It is the unique ID of the site alarm."
            ::= { hwSiteActiveAlarmEntry 1 }

        hwActiveAlarmText OBJECT-TYPE
            SYNTAX OCTET STRING (SIZE (0..63))
            MAX-ACCESS read-only
            STATUS current
            DESCRIPTION
                "Active alarm name. It is of the character string type, and used to specify the content of a specific alarm.  "
            ::= { hwSiteActiveAlarmEntry 2 }

        hwActiveAlarmLevel OBJECT-TYPE
            SYNTAX INTEGER
                {
                critical(1),
                major(2),
                minor(3),
                warning(4),
                unknown(255)
                }
            MAX-ACCESS read-only
            STATUS current
            DESCRIPTION
                "Active alarm level, which users can configure the alarm severity, is an enumeration type:
                    If the enumeration value is 1, it indicates a critical alarm;
                    If the enumeration value is 2, it indicates a major alarm;
                    If the enumeration value is 3, it indicates a minor alarm;
                    If the enumeration value is 4, it indicates a warning alarm;
                    If the enumeration value is 255, it indicates a unknown alarm."
            ::= { hwSiteActiveAlarmEntry 3 }

        hwActiveAlarmSigDesc OBJECT-TYPE
            SYNTAX OCTET STRING (SIZE (0..127))
            MAX-ACCESS read-only
            STATUS current
            DESCRIPTION
                "Active alarm signal description. It is used to add and describe alarm content. Users can define the description of the alarm.
                  Otherwise, the configured character can not be any other languages except English."
            ::= { hwSiteActiveAlarmEntry 4 }

        hwActiveAlarmTime OBJECT-TYPE
            SYNTAX OCTET STRING (SIZE (0..127))
            MAX-ACCESS read-only
            STATUS current
            DESCRIPTION
                "Active alarm time. It is of the character string type, and used to specify the content of a specific alarm.  "
            ::= { hwSiteActiveAlarmEntry 5 }

        hwActiveAlarmRowStatus OBJECT-TYPE
            SYNTAX RowStatus
            MAX-ACCESS read-create
            STATUS current
            DESCRIPTION
                "Rowstatus of active alarm table."
            ::= { hwSiteActiveAlarmEntry 100 }

        hwSMUSiteName OBJECT-TYPE
            SYNTAX OCTET STRING (SIZE (0..63))
            MAX-ACCESS read-only
            STATUS current
            DESCRIPTION
                "Site name, which users can configure, is used to specify a site.  Otherwise, the configured character can not be any other languages except English."
            ::= { hwSiteActiveAlarmEntry 6 }

        hwSMUSiteAdminAddr OBJECT-TYPE
            SYNTAX Unsigned32 (0..65535)
            MAX-ACCESS read-only
            STATUS current
            DESCRIPTION
                "Site administrant address, which users can assigned, is the unique ID of a site. It is used for device management by NMS, and value range is 0 to 65535. "
            ::= { hwSiteActiveAlarmEntry 7 }

        hwSMUNetIdentifier OBJECT-TYPE
            SYNTAX OCTET STRING (SIZE (0..63))
            MAX-ACCESS read-only
            STATUS current
            DESCRIPTION
                "NE ID. It is of the character string type. It is the unique ID of the site (an independent network element (NE)) on the network. Otherwise, the configured character can not be any other languages except English."
            ::= { hwSiteActiveAlarmEntry 8 }

        hwSMUSiteDescription OBJECT-TYPE
            SYNTAX OCTET STRING (SIZE (0..63))
            MAX-ACCESS read-only
            STATUS current
            DESCRIPTION
                "Site description. It is of the character string type. It is used to describe the site information such as the site location, which users can configure.  Otherwise, the configured character can not be any other languages except English."
            ::= { hwSiteActiveAlarmEntry 9 }

        hwEquipId OBJECT-TYPE
            SYNTAX Unsigned32 (0..100)
            MAX-ACCESS read-only
            STATUS current
            DESCRIPTION
                "Equipment ID. Value range: 000,000 to 000,100, in which the first three digits indicate the device type and the last three digits indicate the device SN. "
            ::= { hwSiteActiveAlarmEntry 10 }

        hwEquipName OBJECT-TYPE
            SYNTAX OCTET STRING (SIZE (0..63))
            MAX-ACCESS read-only
            STATUS current
            DESCRIPTION
                "Equipment name. It is of the character string type, and users can set the name of the monitor. 
                Otherwise, the configured character can not be any other languages except English."
            ::= { hwSiteActiveAlarmEntry 11 }

        hwSiteAlarmTable OBJECT-TYPE
            SYNTAX SEQUENCE OF HwSiteAlarmEntry
            MAX-ACCESS not-accessible
             STATUS current
             DESCRIPTION
                "/"
            ::= { hwSiteAlarms 100 }

        hwSiteAlarmEntry OBJECT-TYPE
                        SYNTAX HwSiteAlarmEntry
            MAX-ACCESS not-accessible
             STATUS current
             DESCRIPTION
                "/"
            INDEX { hwAlarmIndex }
            ::= { hwSiteAlarmTable 1 }

        HwSiteAlarmEntry            ::= SEQUENCE {
                hwAlarmIndex
                    Unsigned32,
                hwAlarmText
                    OCTET STRING,
                hwAlarmLevel
                    INTEGER,
                hwAlarmSigDesc
                    OCTET STRING,
                hwAlarmRowStatus
                    RowStatus
            }

        hwAlarmIndex OBJECT-TYPE
            SYNTAX Unsigned32 (1..4294967295)
            MAX-ACCESS read-only
            STATUS current
            DESCRIPTION
                "Site alarm table index. It is the unique ID of the site alarm."
            ::= { hwSiteAlarmEntry 1 }

        hwAlarmText OBJECT-TYPE
            SYNTAX OCTET STRING (SIZE (0..63))
            MAX-ACCESS read-only
            STATUS current
            DESCRIPTION
                "Alarm name. It is of the character string type, and used to specify the content of a specific alarm.  "
            ::= { hwSiteAlarmEntry 2 }

        hwAlarmLevel OBJECT-TYPE
            SYNTAX INTEGER
                {
                critical(1),
                major(2),
                minor(3),
                warning(4),
                unknown(255)
                }
            MAX-ACCESS read-write
            STATUS current
            DESCRIPTION
                "Alarm level, which users can configure the alarm severity, is an enumeration type:
                    If the enumeration value is 1, it indicates a critical alarm;
                    If the enumeration value is 2, it indicates a major alarm;
                    If the enumeration value is 3, it indicates a minor alarm;
                    If the enumeration value is 4, it indicates a warning alarm;
                    If the enumeration value is 255, it indicates a unknown alarm."
            ::= { hwSiteAlarmEntry 3 }

        hwAlarmSigDesc OBJECT-TYPE
            SYNTAX OCTET STRING (SIZE (0..127))
            MAX-ACCESS read-only
            STATUS current
            DESCRIPTION
                "Alarm signal description. It is used to add and describe alarm content. Users can define the description of the alarm. 
                Otherwise, the configured character can not be any other languages except English."
            ::= { hwSiteAlarmEntry 4 }

        hwAlarmRowStatus OBJECT-TYPE
            SYNTAX RowStatus
            MAX-ACCESS read-create
            STATUS current
            DESCRIPTION
                "RowStatus of site alarms table."
            ::= { hwSiteAlarmEntry 100 }

        hwSiteStatus OBJECT IDENTIFIER ::= { hwSiteInfo 3 }

        hwAcInputStatus OBJECT-TYPE
            SYNTAX INTEGER
                {
                disable(1),
                enable(2),
                unknown(255)
                }
            MAX-ACCESS read-only
            STATUS current
            DESCRIPTION
                "AC fail, Enumeration meaning:
                disable(1),enable(2),unknown(255)"
            ::= { hwSiteStatus 1 }

        hwRectifierStatus OBJECT-TYPE
            SYNTAX INTEGER
                {
                disable(1),
                enable(2),
                unknown(255)
                }
            MAX-ACCESS read-only
            STATUS current
            DESCRIPTION
                "Rectifier fault, Enumeration meaning:
                disable(1),enable(2),unknown(255)"
            ::= { hwSiteStatus 2 }

        hwBatteryDischarge OBJECT-TYPE
            SYNTAX INTEGER
                {
                disable(1),
                enable(2),
                unknown(255)
                }
            MAX-ACCESS read-only
            STATUS current
            DESCRIPTION
                "Battery discharge, Enumeration meaning:
                disable(1),enable(2),unknown(255)"
            ::= { hwSiteStatus 3 }

        hwBatteryLowVoltage OBJECT-TYPE
            SYNTAX INTEGER
                {
                disable(1),
                enable(2),
                unknown(255)
                }
            MAX-ACCESS read-only
            STATUS current
            DESCRIPTION
                "Battery low voltage, Enumeration meaning:
                disable(1),enable(2),unknown(255)"
            ::= { hwSiteStatus 4 }

        hwBatteryUltraLowVoltage OBJECT-TYPE
            SYNTAX INTEGER
                {
                disable(1),
                enable(2),
                unknown(255)
                }
            MAX-ACCESS read-only
            STATUS current
            DESCRIPTION
                "Battery ultra-low voltage, Enumeration meaning:
                disable(1),enable(2),unknown(255)"
            ::= { hwSiteStatus 5 }

        hwBatteryDisconnect OBJECT-TYPE
            SYNTAX INTEGER
                {
                disable(1),
                enable(2),
                unknown(255)
                }
            MAX-ACCESS read-only
            STATUS current
            DESCRIPTION
                "Battery disconnect, Enumeration meaning:
                disable(1),enable(2),unknown(255)"
            ::= { hwSiteStatus 6 }

        hwFuseBroken OBJECT-TYPE
            SYNTAX INTEGER
                {
                disable(1),
                enable(2),
                unknown(255)
                }
            MAX-ACCESS read-only
            STATUS current
            DESCRIPTION
                "Load fuse or battery fuse broken, Enumeration meaning:
                disable(1),enable(2),unknown(255)"
            ::= { hwSiteStatus 7 }

        hwLowRecitiferCapacity OBJECT-TYPE
            SYNTAX INTEGER
                {
                disable(1),
                enable(2),
                unknown(255)
                }
            MAX-ACCESS read-only
            STATUS current
            DESCRIPTION
                "large load current and low rectifier capacity, Enumeration meaning:
                disable(1),enable(2),unknown(255)"
            ::= { hwSiteStatus 8 }

        hwBatteryTestNegative OBJECT-TYPE
            SYNTAX INTEGER
                {
                disable(1),
                enable(2),
                unknown(255)
                }
            MAX-ACCESS read-only
            STATUS current
            DESCRIPTION
                "Battery test result negative, Enumeration meaning:
                disable(1),enable(2),unknown(255)"
            ::= { hwSiteStatus 9 }

        hwUrgentAlarmStatus OBJECT-TYPE
            SYNTAX INTEGER
                {
                disable(1),
                enable(2),
                unknown(255)
                }
            MAX-ACCESS read-only
            STATUS current
            DESCRIPTION
                "Urgent Alarm, Enumeration meaning:
                disable(1),enable(2),unknown(255)"
            ::= { hwSiteStatus 10 }

        hwNonurgentAlarmStatus OBJECT-TYPE
            SYNTAX INTEGER
                {
                disable(1),
                enable(2),
                unknown(255)
                }
            MAX-ACCESS read-only
            STATUS current
            DESCRIPTION
                "Non-Urgent Alarm, Enumeration meaning:
                disable(1),enable(2),unknown(255)"
            ::= { hwSiteStatus 11 }

        hwXmuModuleFaultAlarmStatus OBJECT-TYPE
            SYNTAX INTEGER
                {
                noalarm(0),
                alarm(1)
                }
            MAX-ACCESS read-only
            STATUS current
            DESCRIPTION
                "Module fault alarmn
                 0: no alarm, 1:alarm"
            ::= { hwSiteStatus 12 }

        hwLvdDisabledAlarmStatus OBJECT-TYPE
            SYNTAX INTEGER
                {
                noalarm(0),
                alarm(1)
                }
            MAX-ACCESS read-only
            STATUS current
            DESCRIPTION
                "Lvd disabled alarm
                 0: no alarm, 1:alarm"
            ::= { hwSiteStatus 13 }

        hwRectMissingAlarmStatus OBJECT-TYPE
            SYNTAX INTEGER
                {
                noalarm(1),
                alarm(2)
                }
            MAX-ACCESS read-only
            STATUS current
            DESCRIPTION
                "Rect missing alarm
                 1: no alarm, 2:alarm"
            ::= { hwSiteStatus 14 }

        hwSiteMonitors OBJECT IDENTIFIER ::= { hwSiteMonitorMIBObjects 2 }

        hwMonitorsGroup OBJECT IDENTIFIER ::= { hwSiteMonitors 1 }

        hwMonsGroupId OBJECT-TYPE
            SYNTAX Unsigned32
            MAX-ACCESS read-only
            STATUS current
            DESCRIPTION
                "Site monitor group ID, is the unique ID of the site monitors."
            ::= { hwMonitorsGroup 1 }

        hwMonsGroupName OBJECT-TYPE
            SYNTAX OCTET STRING (SIZE (0..63))
            MAX-ACCESS read-write
            STATUS current
            DESCRIPTION
                "Site monitor group name is of the character string type, used to specify the monitor group. Users can configure it. Otherwise, the configured character can not be any other languages except English."
            ::= { hwMonitorsGroup 2 }

        hwMonsQuantity OBJECT-TYPE
            SYNTAX Unsigned32 (0..100)
            MAX-ACCESS read-only
            STATUS current
            DESCRIPTION
                "Total site intelligent monitors. unit:pcs."
            ::= { hwMonitorsGroup 3 }

        hwMonitor OBJECT IDENTIFIER ::= { hwSiteMonitors 2 }

        hwMonitorTable OBJECT-TYPE
            SYNTAX SEQUENCE OF HwMonitorEntry
            MAX-ACCESS not-accessible
             STATUS current
             DESCRIPTION
                "/"
            ::= { hwMonitor 1 }

        hwMonitorEntry OBJECT-TYPE
                        SYNTAX HwMonitorEntry
            MAX-ACCESS not-accessible
             STATUS current
             DESCRIPTION
                "/"
            INDEX { hwMonIndex }
            ::= { hwMonitorTable 1 }

        HwMonitorEntry            ::= SEQUENCE {
                hwMonIndex
                    Integer32,
                hwMonEquipId
                    Unsigned32,
                hwMonEquipName
                    OCTET STRING,
                hwMonEquipDescription
                    OCTET STRING,
                hwMonEquipSoftwareVersion
                    OCTET STRING,
                hwMonEquipPcbVersion
                    OCTET STRING,
                hwMonEquipManufacturer
                    OCTET STRING,
                hwMonEquipManuDate
                    OCTET STRING,
                hwMonEquipSerialNo
                    OCTET STRING,
                hwMonEquipOperTotalTime
                    Unsigned32,
                hwSetMonEquipCtrlState
                    INTEGER,
                hwCtrlMonEquipReset
                    INTEGER,
                hwMonitorOperStatus
                    INTEGER,
                hwMonRowStatus
                    RowStatus
            }

        hwMonIndex OBJECT-TYPE
            SYNTAX Integer32 (1..100)
            MAX-ACCESS read-only
            STATUS current
            DESCRIPTION
                "Table index of the site monitors (hwSiteMonitorTable) is restricted by the quantity of the site monitors (hwMonsQuantity). 
                Value range: 1 to 100."
            ::= { hwMonitorEntry 1 }

        hwMonEquipId OBJECT-TYPE
            SYNTAX Unsigned32
            MAX-ACCESS read-only
            STATUS current
            DESCRIPTION
                "Site monitor ID. 
                Value range: 001,001 to 001,100, in which the first three digits indicate the device type and the last three digits indicate the device SN. "
            ::= { hwMonitorEntry 2 }

        hwMonEquipName OBJECT-TYPE
            SYNTAX OCTET STRING (SIZE (0..63))
            MAX-ACCESS read-write
            STATUS current
            DESCRIPTION
                "Monitor name. It is of the character string type, and users can set the name of the monitor.   
                Otherwise, the configured character can not be any other languages except English."
            ::= { hwMonitorEntry 3 }

        hwMonEquipDescription OBJECT-TYPE
            SYNTAX OCTET STRING (SIZE (0..63))
            MAX-ACCESS read-write
            STATUS current
            DESCRIPTION
                "Monitor description. It is of the character string type. Users can set the description of the monitor. 
                 Otherwise, the configured character can not be any other languages except English."
            ::= { hwMonitorEntry 4 }

        hwMonEquipSoftwareVersion OBJECT-TYPE
            SYNTAX OCTET STRING (SIZE (0..63))
            MAX-ACCESS read-only
            STATUS current
            DESCRIPTION
                "Monitor software version. It is of the character string type."
            ::= { hwMonitorEntry 5 }

        hwMonEquipPcbVersion OBJECT-TYPE
            SYNTAX OCTET STRING (SIZE (0..63))
            MAX-ACCESS read-only
            STATUS current
            DESCRIPTION
                "Monitor printed circuit board (PCB) hardware version. It is of the character string type."
            ::= { hwMonitorEntry 6 }

        hwMonEquipManufacturer OBJECT-TYPE
            SYNTAX OCTET STRING (SIZE (0..63))
            MAX-ACCESS read-only
            STATUS current
            DESCRIPTION
                "Monitor manufacture. It is of the character string type, and is an inherent attribute of the device."
            ::= { hwMonitorEntry 7 }

        hwMonEquipManuDate OBJECT-TYPE
            SYNTAX OCTET STRING (SIZE (0..127))
            MAX-ACCESS read-only
            STATUS current
            DESCRIPTION
                "Monitor production date. It is of the character string type, and is an inherent attribute of the device.  "
            ::= { hwMonitorEntry 8 }

        hwMonEquipSerialNo OBJECT-TYPE
            SYNTAX OCTET STRING (SIZE (0..127))
            MAX-ACCESS read-only
            STATUS current
            DESCRIPTION
                "Production SN of the monitor. It is the electronic tag of the products."
            ::= { hwMonitorEntry 9 }

        hwMonEquipOperTotalTime OBJECT-TYPE
            SYNTAX Unsigned32 (0..65535)
            MAX-ACCESS read-only
            STATUS current
            DESCRIPTION
                "Total monitor runtime. The monitor counts the data in real time. 
                Value range is 0 to 65535,
                The value  is an integer (1), 
                unit:hours. (h). 
                It is used for performance measurement and evaluation of the monitor."
            ::= { hwMonitorEntry 10 }

        hwSetMonEquipCtrlState OBJECT-TYPE
            SYNTAX INTEGER
                {
                manualMode(1),
                autoMode(2),
                unknown(255)
                }
            MAX-ACCESS read-write
            STATUS current
            DESCRIPTION
                "Monitor control status. It is an enumeration type:
                  If the enumeration value is 1, it indicates the background control;
                  If the enumeration value is 2, it indicates the automatic control.
                  If the enumeration value is 255, it indicates monitor module operation status unknown. 
                  In manual state, monitor works under background commands; while monitors runs well automatically in auto state. 
                  For details, see the corresponding user manual of the monitor."
            ::= { hwMonitorEntry 11 }

        hwCtrlMonEquipReset OBJECT-TYPE
            SYNTAX INTEGER
                {
                reset(2),
                unknown(255)
                }
            MAX-ACCESS read-write
            STATUS current
            DESCRIPTION
                "Warm-reset control of the monitor. It is an enumeration type:
                  If the enumeration value is 2, it indicates the Warm-reset control of the monitor is reset.
                  If the enumeration value is 255, it indicates the Warm-reset control of the monito is unknown. "
            ::= { hwMonitorEntry 12 }

        hwMonitorOperStatus OBJECT-TYPE
            SYNTAX INTEGER
                {
                normal(1),
                commRs485Fail(2),
                commNetFail(3),
                fault(4),
                alarmResume(254),
                unknown(255)
                }
            MAX-ACCESS read-only
            STATUS current
            DESCRIPTION
                "State of the site monitor module. It is an enumeration type: 
                  If the enumeration value is 1, it indicates that the site monitor module is in the normal state;
                  If the enumeration value is 2, it indicates that the monitor module RS485 port communication failed; 
                  If the enumeration value is 3, it indicates that the monitor module net port communication failed;  
                  If the enumeration value is 4, it indicates that a fault occurs on the monitor module; 
                  If the enumeration value is 254, it indicates monitor module alarm resume;  
                  If the enumeration value is 255, it indicates monitor module operation status unknown. "
            ::= { hwMonitorEntry 99 }

        hwMonRowStatus OBJECT-TYPE
            SYNTAX RowStatus
            MAX-ACCESS read-create
            STATUS current
            DESCRIPTION
                "RowStatus of site monitor."
            ::= { hwMonitorEntry 100 }

        hwSiteRectifiers OBJECT IDENTIFIER ::= { hwSiteMonitorMIBObjects 3 }

        hwRectsGroup OBJECT IDENTIFIER ::= { hwSiteRectifiers 1 }

        hwRectsGroupId OBJECT-TYPE
            SYNTAX Unsigned32
            MAX-ACCESS read-only
            STATUS current
            DESCRIPTION
                "Device group ID of the rectifier module. It is the unique ID of the rectifier module group, and its default value: 002,000. 
                  The first digits indicate the device type and the last three digits indicate the device SN. If the last three digits are 000, it indicates a virtual device. "
            ::= { hwRectsGroup 1 }

        hwRectsGroupName OBJECT-TYPE
            SYNTAX OCTET STRING (SIZE (0..63))
            MAX-ACCESS read-write
            STATUS current
            DESCRIPTION
                "Name of the rectifier module group, character string type, is used to specify the rectifier module group. Users can configure it.  
                Otherwise, the configured character can not be any other languages except English."
            ::= { hwRectsGroup 2 }

        hwRectsTotalCurrent OBJECT-TYPE
            SYNTAX Unsigned32 (0..240000)
            MAX-ACCESS read-only
            STATUS current
            DESCRIPTION
                "Total current of the rectifier module group on the site. It indicates the real-time statistics of the rectifier module group on the site. 
                Default value: 0.0 to 24000.0, 
                unit: A, 
                and the value is accurate to one decimal place (.1). 
                If the value is 2147483647(0x7FFFFFFF), it indicates that the value is invalid."
            ::= { hwRectsGroup 3 }

        hwRectsTotalQuantity OBJECT-TYPE
            SYNTAX Unsigned32 (0..288)
            MAX-ACCESS read-only
            STATUS current
            DESCRIPTION
                "Total quantity of the rectifier modules. 
                Value range: 0 to 288. unit:pcs."
            ::= { hwRectsGroup 4 }

        hwRectsRatedVoltage OBJECT-TYPE
            SYNTAX Unsigned32 (420..583)
            MAX-ACCESS read-only
            STATUS current
            DESCRIPTION
                "Rated voltage of the rectifier module group. It is an inherent attribute. 
                Value range: 42 to 58.3,
                unit: V, 
                and the value is accurate to one decimal place (.1). 
                 If the value is 2147483647(0x7FFFFFFF), it indicates that the value is invalid."
            ::= { hwRectsGroup 5 }

        hwModifyRectsOutputVoltage OBJECT-TYPE
            SYNTAX Unsigned32 (420..580)
            MAX-ACCESS read-write
            STATUS current
            DESCRIPTION
                "Voltage adjustment of the rectifier module, which users can configure it. 
                Value range: 42 to 58,
                unit: V, 
                and the value is accurate to one decimal space (.1). 
                Based on the actual requirements, users can modify the output voltage of the rectifier module by modifying the value of the node. 
                If the value is 2147483647(0x7FFFFFFF), it indicates that the value is invalid.
                NOTES: Be cautious about changing the value of the node.  Only the system in manual mode, this parameter can be configured successfully."
            ::= { hwRectsGroup 6 }

        hwSetRectsRedundEnable OBJECT-TYPE
            SYNTAX INTEGER
                {
                disable(1),
                enable(2),
                funcNotSupport(3)
                }
            MAX-ACCESS read-write
            STATUS current
            DESCRIPTION
                "Sleep function of the rectifier module group on the site. It is an enumeration value:
                If the NMS notifies the SNMP agent that this node is set to 1, it means to disable the sleep function of the rectifier module group;
                If the NMS notifies the SNMP agent that this node is set to 2, it means to enable the sleep function of the rectifier module group.
                If NMS get the node value is 3, it indicates that this function is not support, 
                and in such case the value set to the agent is invalid.
                Default value: to disable the sleep function of the rectifier module group. For details, see the corresponding user manual of the monitor."
            ::= { hwRectsGroup 7 }

        hwCtrlRectsAllOnOff OBJECT-TYPE
            SYNTAX INTEGER
                {
                on(1),
                nullOper(255)
                }
            MAX-ACCESS read-write
            STATUS current
            DESCRIPTION
                "Power-on or power-off of the rectifier module group (all the rectifier modules) on the site. It is an enumeration value:
                If the NMS notifies the SNMP agent that this node is set to 1, it indicates power-on of all rectifier modules;
                If the NMS notifies the SNMP agent that this node is set to 255, it indicates nullOper of all the rectifier modules.
                NOTE: Only the system in manual mode, this parameter can be configured successfully."
            ::= { hwRectsGroup 8 }

        hwRectsTotalDCPower OBJECT-TYPE
            SYNTAX Unsigned32 (0..100000000)
            MAX-ACCESS read-only
            STATUS current
            DESCRIPTION
                "Total power of the direct current output.
                Value range: 0 to 100000000,
                unit: W, 
                and the value is an integer.
                If the value is 2147483647(0x7FFFFFFF), it indicates that the value is invalid."
            ::= { hwRectsGroup 9 }

        hwRectsLoadUsage OBJECT-TYPE
            SYNTAX Unsigned32 (0..150)
            MAX-ACCESS read-only
            STATUS current
            DESCRIPTION
                "Load Usage.
                Value range: 0 to 150, 
                unit: %, 
                and the value is an integer. 
                If the value is 2147483647(0x7FFFFFFF), it indicates that the value is invalid."
            ::= { hwRectsGroup 10 }

        hwRectsTotalACInputPower OBJECT-TYPE
            SYNTAX Unsigned32 (0..100000000)
            MAX-ACCESS read-only
            STATUS current
            DESCRIPTION
                "Total power of the direct current output. 
                Value range: 0 to 100000000, 
                unit: W, 
                and the value is an integer. 
                If the value is 2147483647(0x7FFFFFFF), it indicates that the value is invalid."
            ::= { hwRectsGroup 11 }

        hwRectsHighRectifierCapacity OBJECT-TYPE
            SYNTAX Unsigned32 (0..150)
            MAX-ACCESS read-write
            STATUS current
            DESCRIPTION
                "High rectifier capacity. 
                Value range: 0 to 150, 
                unit: %, 
                and the value is an integer. 
                If the value is 2147483647(0x7FFFFFFF), it indicates that the value is invalid."
            ::= { hwRectsGroup 12 }

        hwRectsLowRectifierCapacity OBJECT-TYPE
            SYNTAX Unsigned32 (0..150)
            MAX-ACCESS read-write
            STATUS current
            DESCRIPTION
                "Low rectifier capacity. 
                Value range: 0 to 150, 
                unit: %, 
                and the value is an integer. 
                If the value is 2147483647(0x7FFFFFFF), it indicates that the value is invalid."
            ::= { hwRectsGroup 13 }

        hwRectsOverVoltProtThres OBJECT-TYPE
            SYNTAX Unsigned32 (560..605)
            MAX-ACCESS read-write
            STATUS current
            DESCRIPTION
                "Overvoltage protection threshold. 
                Value range: 56.0 to 60.5, 
                unit: V, 
                and the value is accurate to one decimal space (.1). 
                If the value is 2147483647(0x7FFFFFFF), it indicates that the value is invalid."
            ::= { hwRectsGroup 14 }

        hwRectsWalkinEnable OBJECT-TYPE
            SYNTAX INTEGER
                {
                no(1),
                yes(2),
                unknown(255)
                }
            MAX-ACCESS read-write
            STATUS current
            DESCRIPTION
                "Walk-In Enable.Value range: no is 0, yes is 1."
            ::= { hwRectsGroup 16 }

        hwRectsWalkinTime OBJECT-TYPE
            SYNTAX Unsigned32 (8..200)
            MAX-ACCESS read-write
            STATUS current
            DESCRIPTION
                "Walk-In Time.Value range: 8 to 200, unit: s."
            ::= { hwRectsGroup 17 }

        hwRectifier OBJECT IDENTIFIER ::= { hwSiteRectifiers 2 }

        hwRectConfigTable OBJECT-TYPE
            SYNTAX SEQUENCE OF HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            ::= { hwRectifier 1 }

        hwRectConfigEntry OBJECT-TYPE
                        SYNTAX HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            INDEX { hwRectConfigIndex }
            ::= { hwRectConfigTable 1 }

        HwRectConfigEntry            ::= SEQUENCE {
                hwRectConfigIndex
                    Integer32,
                hwRectEquipId
                    Unsigned32,
                hwRectEquipName
                    OCTET STRING,
                hwRectSoftwareVersion
                    OCTET STRING,
                hwRectSerialNo
                    OCTET STRING,
                hwRectRatedCurrent
                    Unsigned32,
                hwRectEfficency
                    Unsigned32,
                hwRectFatherEquipName
                    OCTET STRING,
                hwRectModelType
                    OCTET STRING
            }

        hwRectConfigIndex OBJECT-TYPE
            SYNTAX Integer32 (1..256)
            MAX-ACCESS read-only
            STATUS current
            DESCRIPTION
                "Index of the device configuration list for the rectifier modules, which value range: 1 to 256(To the actual subject). Lines of the device list are restricted by the total quantity of the rectifier modules (hwRectsTotalQuantity)."
            ::= { hwRectConfigEntry 1 }

        hwRectEquipId OBJECT-TYPE
            SYNTAX Unsigned32
            MAX-ACCESS read-only
            STATUS current
            DESCRIPTION
                "Device ID of the rectifier."
            ::= { hwRectConfigEntry 2 }

        hwRectEquipName OBJECT-TYPE
            SYNTAX OCTET STRING (SIZE (0..63))
            MAX-ACCESS read-only
            STATUS current
            DESCRIPTION
                "Device name of the rectifier module."
            ::= { hwRectConfigEntry 3 }

        hwRectSoftwareVersion OBJECT-TYPE
            SYNTAX OCTET STRING (SIZE (0..63))
            MAX-ACCESS read-only
            STATUS current
            DESCRIPTION
                "Software version of the rectifier module. It indicates the software version ID of the module. "
            ::= { hwRectConfigEntry 5 }

        hwRectSerialNo OBJECT-TYPE
            SYNTAX OCTET STRING (SIZE (0..127))
            MAX-ACCESS read-only
            STATUS current
            DESCRIPTION
                "Rectifier module SN. It indicates the electronic tag of the product."
            ::= { hwRectConfigEntry 8 }

        hwRectRatedCurrent OBJECT-TYPE
            SYNTAX Unsigned32 (0..2000)
            MAX-ACCESS read-only
            STATUS current
            DESCRIPTION
                "Rated current of the rectifier module, is an inherent attribute. Value range: 0 to 200, unit: A, and the value is accurate to one decimal place (.1). If the value is 2147483647(0x7FFFFFFF), it indicates that the value is invalid."
            ::= { hwRectConfigEntry 9 }

        hwRectEfficency OBJECT-TYPE
            SYNTAX Unsigned32 (0..100)
            MAX-ACCESS read-only
            STATUS current
            DESCRIPTION
                "Efficiency of the rectifier module, is an inherent attribute. 
                Value range: 0 to 100, 
                unit: %, 
                If the value is 2147483647(0x7FFFFFFF), it indicates that the value is invalid."
            ::= { hwRectConfigEntry 10 }

        hwRectFatherEquipName OBJECT-TYPE
            SYNTAX OCTET STRING
            MAX-ACCESS read-only
            STATUS current
            DESCRIPTION
                "Name of the parent device of the Rectifier"
            ::= { hwRectConfigEntry 14 }

        hwRectModelType OBJECT-TYPE
            SYNTAX OCTET STRING (SIZE (0..100))
            MAX-ACCESS read-only
            STATUS current
            DESCRIPTION
                "PSU module model."
            ::= { hwRectConfigEntry 15 }

        hwRectOperTable OBJECT-TYPE
            SYNTAX SEQUENCE OF HwRectOperEntry
            MAX-ACCESS not-accessible
             STATUS current
             DESCRIPTION
                "Rectifier runing information table. Use this table to get rectifiers output current, output voltage, totle runing time, and current run status. 
                This table's index is hwRectRunIndex, clone rectifier runing information table."
            ::= { hwRectifier 2 }

        hwRectOperEntry OBJECT-TYPE
                        SYNTAX HwRectOperEntry
            MAX-ACCESS not-accessible
             STATUS current
             DESCRIPTION
                "Rectifier runing information table. Use this table to get rectifiers output current, output voltage, totle runing time, and current run status. 
                This table's index is hwRectRunIndex, clone rectifier runing information table."
            INDEX { hwRectOperIndex }
            ::= { hwRectOperTable 1 }

        HwRectOperEntry            ::= SEQUENCE {
                hwRectOperIndex
                    Integer32,
                hwRectOutputCurrent
                    Unsigned32,
                hwRectOutputVoltage
                    Unsigned32,
                hwRectDCOutputPower
                    Unsigned32,
                hwRectACVoltage
                    Unsigned32,
                hwRectRatedEfficiency
                    Unsigned32,
                hwRectifierTemperature
                    Integer32,
                hwRectOperStatus
                    INTEGER,
                hwRectOperRowStatus
                    RowStatus
            }

        hwRectOperIndex OBJECT-TYPE
            SYNTAX Integer32 (1..256)
            MAX-ACCESS read-only
            STATUS current
            DESCRIPTION
                "Table index of the running rectifier modules, 
                which value range: 1 to 256(To the actual subject). 
                Lines of the device list are restricted by the total quantity of the rectifier modules (hwRectsTotalQuantity)."
            ::= { hwRectOperEntry 1 }

        hwRectOutputCurrent OBJECT-TYPE
            SYNTAX Unsigned32 (0..3000)
            MAX-ACCESS read-only
            STATUS current
            DESCRIPTION
                "Output current of the rectifier module. It is a real-time analog parameter. 
                Value range: 0 to 300, 
                unit: A, 
                and the value is accurate to one decimal place (.1). 
                If the value is 2147483647(0x7FFFFFFF), it indicates that the value is invalid."
            ::= { hwRectOperEntry 2 }

        hwRectOutputVoltage OBJECT-TYPE
            SYNTAX Unsigned32 (0..1000)
            MAX-ACCESS read-only
            STATUS current
            DESCRIPTION
                "Output voltage of the rectifier module. It is a real-time analog parameter. 
                Value range: 0 to 100, 
                unit: V, 
                the value is accurate to one decimal place (.1). 
                If the value is 2147483647(0x7FFFFFFF), it indicates that the value is invalid. "
            ::= { hwRectOperEntry 3 }

        hwRectDCOutputPower OBJECT-TYPE
            SYNTAX Unsigned32 (0..30000)
            MAX-ACCESS read-only
            STATUS current
            DESCRIPTION
                "DC output power. 
                Value range: 0.000 to 30.000, 
                unit: kW, 
                and the value is accurate to three decimal space (.01). 
                If the value is 2147483647(0x7FFFFFFF), it indicates that the value is invalid."
            ::= { hwRectOperEntry 5 }

        hwRectACVoltage OBJECT-TYPE
            SYNTAX Unsigned32 (0..6000)
            MAX-ACCESS read-only
            STATUS current
            DESCRIPTION
                "AC input voltage. 
                Value range: 0 to 600, 
                unit: V, 
                and the value is accurate to one decimal space (.1).
                If the value is 2147483647(0x7FFFFFFF), it indicates that the value is invalid."
            ::= { hwRectOperEntry 6 }

        hwRectRatedEfficiency OBJECT-TYPE
            SYNTAX Unsigned32 (0..100)
            MAX-ACCESS read-only
            STATUS current
            DESCRIPTION
                "Rated Efficiency. 
                Value range: 0 to 100, 
                unit: %, 
                and the value is an integer.(1). 
                If the value is 2147483647(0x7FFFFFFF), it indicates that the value is invalid."
            ::= { hwRectOperEntry 7 }

        hwRectifierTemperature OBJECT-TYPE
            SYNTAX Integer32 (-3000..3000)
            MAX-ACCESS read-only
            STATUS current
            DESCRIPTION
                "Rectifier Temperature. 
                Value range: -300 to 300, 
                unit: degC, 
                and the value is accurate to one decimal space (.1). 
                If the value is 2147483647(0x7FFFFFFF), it indicates that the value is invalid."
            ::= { hwRectOperEntry 8 }

        hwRectOperStatus OBJECT-TYPE
            SYNTAX INTEGER
                {
                normal(1),
                fault(2),
                protect(3),
                commFail(4),
                switchOff(5),
                invalid(6),
                noConfig(7),
                acOff(8),
                rectLost(9),
                alarmResume(254),
                unknown(255)
                }
            MAX-ACCESS read-only
            STATUS current
            DESCRIPTION
                "State of the rectifier module. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                If the enumeration value is 8, this rectifier is ac off;
                If the enumeration value is 9, this rectifier is rectLost;
                  If the enumeration value is 254, rectifier alarm resume; 
                  If the enumeration value is 255, rectifier operation status unknown."
            ::= { hwRectOperEntry 99 }

        hwRectOperRowStatus OBJECT-TYPE
            SYNTAX RowStatus
            MAX-ACCESS read-create
            STATUS current
            DESCRIPTION
                "RowStatus of rectifier runing table."
            ::= { hwRectOperEntry 100 }

        hwSiteBatterys OBJECT IDENTIFIER ::= { hwSiteMonitorMIBObjects 4 }

        hwBattsConfig OBJECT IDENTIFIER ::= { hwSiteBatterys 1 }

        hwBattsGroupId OBJECT-TYPE
            SYNTAX Unsigned32
            MAX-ACCESS read-only
            STATUS current
            DESCRIPTION
                "Battery group ID. It is the unique ID of the battery group device. 
                The first digits indicate the device type and the last three digits indicate the device SN. 
                If the last three digits are 000, it indicates a virtual device. "
            ::= { hwBattsConfig 1 }

        hwBattsGroupName OBJECT-TYPE
            SYNTAX OCTET STRING (SIZE (0..63))
            MAX-ACCESS read-write
            STATUS current
            DESCRIPTION
                "Device name of the battery group. It is of the character string type, which can be configured by users. 
                Otherwise, the configured character can not be any other languages except English."
            ::= { hwBattsConfig 2 }

        hwBattsTotalQuantity OBJECT-TYPE
            SYNTAX Unsigned32 (0..16)
            MAX-ACCESS read-only
            STATUS current
            DESCRIPTION
                "Total quantity of battery strings, 
                which value range: 0 to 16. 
                unit:strings."
            ::= { hwBattsConfig 3 }

        hwSetBattsHighTempAction OBJECT-TYPE
            SYNTAX INTEGER
                {
                blvd(1),
                lowerDcOutput(2),
                disable(3),
                unknown(255)
                }
            MAX-ACCESS read-write
            STATUS current
            DESCRIPTION
                "Battery high-temperature protection mode. It is an enumeration value, and can be configured. 
                If the enumeration value is 1, it indicates the blvd mode;
                If the enumeration value is 2, it indicates the protection mode of lowering the output voltage of the rectifier module. 
                If the enumeration value is 3, it indicates the disable mode;
                If the enumeration value is 255, it indicates do nothing. 
                Note: This MIB node has been specially processed using the RegisterDifferSignalHandleType() method, and the node values and signal values have a non enumeration mapping relationship."
            ::= { hwBattsConfig 4 }

        hwSetBattsHighTempVoltLimit OBJECT-TYPE
            SYNTAX Unsigned32 (420..530)
            MAX-ACCESS read-write
            STATUS current
            DESCRIPTION
                "Battery protection voltage under high temperature. It works with the low-voltage power-off protection in battery high-temperature protection mode, which can be configured by users. 
                If the low-voltage power-off protection mode (that is, the enumeration value is 1) is selected, the node is a low-voltage power-off node. 
                Value range: 42 to 53, 
                unit: V, 
                and the value is accurate to one decimal place (.1).  
                If the value is 2147483647(0x7FFFFFFF), it indicates that the value is invalid."
            ::= { hwBattsConfig 5 }

        hwSetBattsHTDLimit OBJECT-TYPE
            SYNTAX Integer32 (25..80)
            MAX-ACCESS read-write
            STATUS current
            DESCRIPTION
                "Upper threshold of the battery high temperature disconnection(HTD), can be configured by users. 
                Value range: 25 to 80, 
                unit: centigrade (degC), 
                and the value is an integer (1). 
                If the value is 2147483647(0x7FFFFFFF), it indicates that the value is invalid.
                NOTE: There is linkage between hwSetBattsHTDLimit and hwSetBattsTempUpperLimit"
            ::= { hwBattsConfig 6 }

        hwSetBattsHTDEnable OBJECT-TYPE
            SYNTAX INTEGER
                {
                enable(1),
                disable(2)
                }
            MAX-ACCESS read-write
            STATUS current
            DESCRIPTION
                "Battery high temperature disconnection enable. It is an enumeration type:
                  If the enumeration value is 1, enable the operation of the battery disconnection in high temperature; 
                  If the enumeration value is 2, disable the operation of the battery disconnection in high temperature. 
                  The operation of the battery disconnection in high temperature is disabled by default. "
            ::= { hwBattsConfig 7 }

        hwSetBattsFloatVoltage OBJECT-TYPE
            SYNTAX Unsigned32 (420..580)
            MAX-ACCESS read-write
            STATUS current
            DESCRIPTION
                "Float charge voltage of the batteries, can be configured by users. 
                Value range: 42.0 to 58.0, 
                unit: V, 
                and the value is accurate to one decimal place (.1) 
                If the value is 2147483647(0x7FFFFFFF), it indicates that the value is invalid.
                NOTE: There is linkage between hwSetBattsFloatVoltage and hwSetBattsBoostVoltage
                "
            ::= { hwBattsConfig 8 }

        hwSetBattsBoostVoltage OBJECT-TYPE
            SYNTAX Unsigned32 (420..580)
            MAX-ACCESS read-write
            STATUS current
            DESCRIPTION
                "Boostcharge voltage of the batteries, can be configured by users. 
                Value range: 42.0 to 58.0, 
                unit: V, 
                and the value is accurate to one decimal place (.1). 
                If the value is 2147483647(0x7FFFFFFF), it indicates that the value is invalid.
                NOTE: There is linkage between hwSetBattsFloatVoltage and hwSetBattsBoostVoltage"
            ::= { hwBattsConfig 9 }

        hwSetBattsCurrLimitCoefficient OBJECT-TYPE
            SYNTAX Unsigned32 (5..50)
            MAX-ACCESS read-write
            STATUS current
            DESCRIPTION
                "Current-limiting point coefficient of the batteries, can be configured by users. 
                Value range: 0.05 to 0.5, 
                unit: C10, 
                and the value is accurate to two decimal places (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 10 }

        hwSetBattsCompFactor OBJECT-TYPE
            SYNTAX Unsigned32 (0..150)
            MAX-ACCESS read-write
            STATUS current
            DESCRIPTION
                "Temperature compensated coefficient of the batteries, can be configured by user. 
                Value range: 0 to 150, 
                unit: mv per centigrade, 
                and the value is an integer (1). 
                If the value is 2147483647(0x7FFFFFFF), it indicates that the value is invalid."
            ::= { hwBattsConfig 11 }

        hwCtrlBattsBoostFloat OBJECT-TYPE
            SYNTAX INTEGER
                {
                floatCharge(1),
                boostCharge(2),
                nullOper(255)
                }
            MAX-ACCESS read-write
            STATUS current
            DESCRIPTION
                "Control batteries charge mode between boost and float. It is an enumeration value. 
                  Users actively control the conversion. 
                  If the NMS notifies the SNMP agent that this node is set to 1, it means to start the float charge mode of the batteries; 
                  If the NMS notifies the SNMP agent that this node is set to 2, it means to start the boost charge mode of the batteries. 
                  If the NMS notifies the SNMP agent that this node is set to 255, it means to start the mode of the batteries is nullOper. "
            ::= { hwBattsConfig 12 }

        hwSetBattsRatedCapacity OBJECT-TYPE
            SYNTAX Unsigned32 (5..12000)
            MAX-ACCESS read-write
            STATUS current
            DESCRIPTION
                "Set batteries rated capacity. It is an analog parameter collected by the battery string in real time.
                Value range: 5 to 12000, 
                unit: Ah, 
                the value is an integer (1). 
                If the value is 2147483647(0x7FFFFFFF), it indicates that the value is invalid."
            ::= { hwBattsConfig 13 }

        hwSetBattsTimedBoostChargeEnabled OBJECT-TYPE
            SYNTAX INTEGER
                {
                disable(1),enable(2),unknown(255)
                }
            MAX-ACCESS read-write
            STATUS current
            DESCRIPTION
                "Timed Boost Charge Enabled. It is an enumeration value, and can be configured. 
                If the enumeration value is 1, it indicates timed boost charge is disabled;
                If the enumeration value is 2, it indicates timed boost charge is enabled. 
                If the enumeration value is 255, it indicates timed boost charge is unknown. "
            ::= { hwBattsConfig 14 }

        hwSetBattsTimedBoostChargePeriod OBJECT-TYPE
            SYNTAX Unsigned32 (1..365)
            MAX-ACCESS read-write
            STATUS current
            DESCRIPTION
                "Timed Boost Charge Interval. 
                Value range: 1 to 365, 
                unit: Day, 
                and the value is an integer. 
                If the value is 2147483647(0x7FFFFFFF), it indicates that the value is invalid."
            ::= { hwBattsConfig 15 }

        hwSetBattsMaxTimedBCDuration OBJECT-TYPE
            SYNTAX Unsigned32 (1..24)
            MAX-ACCESS read-write
            STATUS current
            DESCRIPTION
                "Maximum Timed Boost Charge Duration. 
                Value range: 1 to 24, 
                unit: h, 
                and the value is an integer.(1). 
                If the value is 2147483647(0x7FFFFFFF), it indicates that the value is invalid."
            ::= { hwBattsConfig 16 }

        hwSetBattsChargeOvercurAlmThreshold OBJECT-TYPE
            SYNTAX Unsigned32 (5..100)
            MAX-ACCESS read-write
            STATUS current
            DESCRIPTION
                "Charge Overcurrent Alarm Threshold. 
                Value range: 0.05 to 1, 
                unit: C10, 
                and the value is accurate to two decimal space (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 17 }

        hwSetBattsLowCapacityAlarmThreshold OBJECT-TYPE
            SYNTAX Unsigned32 (0..90)
            MAX-ACCESS read-write
            STATUS current
            DESCRIPTION
                "Low Capacity Alarm Threshold. 
                Value range: 0 to 90, 
                unit: %, 
                and the value is an integer. (1)
                If the value is 2147483647(0x7FFFFFFF), it indicates that the value is invalid."
            ::= { hwBattsConfig 18 }

        hwSetBattsBatteryFactory OBJECT-TYPE
            SYNTAX INTEGER
                {
                agisson(1),
                coslight(2),
                dengta(3),
                eltek(4),
                enerSys(5),
                exide(6),
                leoch(7),
                narada(8),
                northStar(9),
                shoto(10),
                others(11),
                unknown(255)
                }
            MAX-ACCESS read-write
            STATUS current
            DESCRIPTION
                "Manufacturer of the battery. It is an enumeration value, and can be configured. "
            ::= { hwBattsConfig 20 }

        hwSetBattsBattaryType OBJECT-TYPE
            SYNTAX INTEGER
                {
                shoto_6-FMX(1),
                shoto_6-XFMJ(2),
                shoto_GFM(3),
                coslight_6-GFM-X(4),
                narada_6-GFM-F(5),
                narada_12NDF(6),
                dengta_6-GFMF(7),
                enersys_12TD-F(8),
                enersys_SBS-F(9),
                northstar_Blue(10),
                northstar_Red(11),
                leoch_LPF12(12),
                exide_M12V_FT(13),
                vrla(14),
                agisson_BERU-TCB-B(15),
                agisson_DCB-A(16),
                agisson_DCB-A1(17),
                agisson_DCB-B(18),
                agisson_DCB-Y(19),
                agisson_FCB(20),
                agisson_FCB-B(21),
                agisson_SCB(22),
                agisson_SCB-A1(23),
                agisson_TCB-A(24),
                agisson_TCB-C(25),
                agisson_TCB-A1(26),
                agisson_TCB-C1(27),
                unknown(255)
                }
            MAX-ACCESS read-write
            STATUS current
            DESCRIPTION
                "Model  of the battery. It is an enumeration value, and can be configured."
            ::= { hwBattsConfig 21 }

        hwBatsTempCompCenterPoint OBJECT-TYPE
            SYNTAX Unsigned32 (5..45)
            MAX-ACCESS read-write
            STATUS current
            DESCRIPTION
                "Temperature compensation center point.Value range: 5 to 45, unit: ℃"
            ::= { hwBattsConfig 22 }

        hwBatsShutMaxVolt OBJECT-TYPE
            SYNTAX Unsigned32 (5..150)
            MAX-ACCESS read-only
            STATUS current
            DESCRIPTION
                "Shunt maximum voltage.Value range: 5 to 150, unit: Mv"
            ::= { hwBattsConfig 23 }

        hwBatsShutMaxCurr OBJECT-TYPE
            SYNTAX Unsigned32 (5..5000)
            MAX-ACCESS read-only
            STATUS current
            DESCRIPTION
                "Current shunt max.Value range: 5 to 5000, unit: A"
            ::= { hwBattsConfig 24 }

        hwBatsBat1Access OBJECT-TYPE
            SYNTAX INTEGER
                {
                no(1),
                yes(2),
                unknown(255)
                }
            MAX-ACCESS read-write
            STATUS current
            DESCRIPTION
                "Battery 1 access.Value range: no is 0, yes is 1."
            ::= { hwBattsConfig 25 }

        hwBatsBat2Access OBJECT-TYPE
            SYNTAX INTEGER
                {
                no(1),
                yes(2),
                unknown(255)
                }
            MAX-ACCESS read-write
            STATUS current
            DESCRIPTION
                "Battery 2 access.Value range: no is 0, yes is 1."
            ::= { hwBattsConfig 26 }

        hwBatsBat3Access OBJECT-TYPE
            SYNTAX INTEGER
                {
                no(1),
                yes(2),
                unknown(255)
                }
            MAX-ACCESS read-write
            STATUS current
            DESCRIPTION
                "Battery 3 access.Value range: no is 0, yes is 1."
            ::= { hwBattsConfig 27 }

        hwBatsBat4Access OBJECT-TYPE
            SYNTAX INTEGER
                {
                no(1),
                yes(2),
                unknown(255)
                }
            MAX-ACCESS read-write
            STATUS current
            DESCRIPTION
                "Battery 4 access.Value range: no is 0, yes is 1."
            ::= { hwBattsConfig 28 }

        hwBatsBat5Access OBJECT-TYPE
            SYNTAX INTEGER
                {
                no(1),
                yes(2),
                unknown(255)
                }
            MAX-ACCESS read-write
            STATUS current
            DESCRIPTION
                "Battery 5 access.Value range: no is 0, yes is 1."
            ::= { hwBattsConfig 29 }

        hwBatsBat6Access OBJECT-TYPE
            SYNTAX INTEGER
                {
                no(1),
                yes(2),
                unknown(255)
                }
            MAX-ACCESS read-write
            STATUS current
            DESCRIPTION
                "Battery 6 access.Value range: no is 0, yes is 1."
            ::= { hwBattsConfig 30 }

        hwBatsBat7Access OBJECT-TYPE
            SYNTAX INTEGER
                {
                no(1),
                yes(2),
                unknown(255)
                }
            MAX-ACCESS read-write
            STATUS current
            DESCRIPTION
                "Battery 7 access.Value range: no is 0, yes is 1."
            ::= { hwBattsConfig 31 }

        hwBatsBat8Access OBJECT-TYPE
            SYNTAX INTEGER
                {
                no(1),
                yes(2),
                unknown(255)
                }
            MAX-ACCESS read-write
            STATUS current
            DESCRIPTION
                "Battery 8 access.Value range: no is 0, yes is 1."
            ::= { hwBattsConfig 32 }

        hwBatsBat9Access OBJECT-TYPE
            SYNTAX INTEGER
                {
                no(1),
                yes(2),
                unknown(255)
                }
            MAX-ACCESS read-write
            STATUS current
            DESCRIPTION
                "Battery 9 access.Value range: no is 0, yes is 1."
            ::= { hwBattsConfig 33 }

        hwBatsBat10Access OBJECT-TYPE
            SYNTAX INTEGER
                {
                no(1),
                yes(2),
                unknown(255)
                }
            MAX-ACCESS read-write
            STATUS current
            DESCRIPTION
                "Battery 10 access.Value range: no is 0, yes is 1."
            ::= { hwBattsConfig 34 }

        hwBatsBat11Access OBJECT-TYPE
            SYNTAX INTEGER
                {
                no(1),
                yes(2),
                unknown(255)
                }
            MAX-ACCESS read-write
            STATUS current
            DESCRIPTION
                "Battery 11 access.Value range: no is 0, yes is 1."
            ::= { hwBattsConfig 35 }

        hwBatsBat12Access OBJECT-TYPE
            SYNTAX INTEGER
                {
                no(1),
                yes(2),
                unknown(255)
                }
            MAX-ACCESS read-write
            STATUS current
            DESCRIPTION
                "Battery 12 access.Value range: no is 0, yes is 1."
            ::= { hwBattsConfig 36 }

        hwBattsOperate OBJECT IDENTIFIER ::= { hwSiteBatterys 2 }

        hwBattsTotalCurrent OBJECT-TYPE
            SYNTAX Integer32 ( -4000000..4000000)
            MAX-ACCESS read-only
            STATUS current
            DESCRIPTION
                "Total current of the battery group. It indicates the real-time statistics of the battery group on the site. 
                Value range: -400000 to +400000, 
                unit: A, 
                and the value is accurate to one decimal place (.1).  
                If the value is 2147483647(0x7FFFFFFF), it indicates that the value is invalid."
            ::= { hwBattsOperate 1 }

        hwBattsPreDischargeTime OBJECT-TYPE
            SYNTAX Unsigned32 (0..15360)
            MAX-ACCESS read-only
            STATUS current
            DESCRIPTION
                "Battery group backup time. It indicates the real-time statistics of the battery group. 
                Value range: 0 to 15360, 
                unit: minutes (min),  
                and the value is an integer (1).  
                If the value is 2147483647(0x7FFFFFFF), it indicates that the value is invalid."
            ::= { hwBattsOperate 2 }

        hwBattsChargeStatus OBJECT-TYPE
            SYNTAX INTEGER
                {
                floatCharge(1),
                boostCharge(2),
                disCharge(3),
                hibernating(4),
                offline(7),
                charge(8),
                unknown(255)
                }
            MAX-ACCESS read-only
            STATUS current
            DESCRIPTION
                "Battery charging state, indicates the charging and discharging information about the battery group. It is an enumeration type. 
                If the enumeration value is 1, it indicates a battery group in the float charging state. 
                If the enumeration value is 2, it indicates a battery group in the boost charging state. 
                If the enumeration value is 3, it indicates a battery group in the discharging state. 
                If the enumeration value is 4, it indicates a battery group in the hibernating state.
                If the enumeration value is 7, it indicates a battery group in the Offline state.
                If the enumeration value is 8, it indicates a battery group in the Charge state.
                If the enumeration value is 255, it indicates a battery group in the Offline state. "
            ::= { hwBattsOperate 3 }

        hwBattsCurrLimitStatus OBJECT-TYPE
            SYNTAX INTEGER
                {
                unlimited(1),
                limited(2),
                unknown(255)
                }
            MAX-ACCESS read-only
            STATUS current
            DESCRIPTION
                "Battery group current-limiting state, indicates the state information about the battery group. It is an enumeration value. 
                  If the enumeration value is 1, it indicates that the current of the battery group is not limited. 
                  If the enumeration value is 2, it indicates the current of the battery group is limited.
                  If the enumeration value is 255, it indicates the current of the battery group is unknown. "
            ::= { hwBattsOperate 4 }

        hwBattsTemprature1 OBJECT-TYPE
            SYNTAX Integer32 ( -300..200)
            MAX-ACCESS read-only
            STATUS current
            DESCRIPTION
                "Battery temperature. It is a battery parameter collected in real time. 
                Value range: -300 to 200, 
                unit: centigrade (degC), 
                and the value is an integer .
                If the value is 2147483647(0x7FFFFFFF), it indicates that battery temperature sensor is not configured."
            ::= { hwBattsOperate 5 }

        hwBattsTemprature2 OBJECT-TYPE
            SYNTAX Integer32 ( -50..100)
            MAX-ACCESS read-only
            STATUS current
            DESCRIPTION
                "Battery temperature. It is a battery parameter collected in real time. 
                Value range: -50 to +100, 
                unit: centigrade (degC), 
                and the value is an integer (1).
                If the value is 2147483647(0x7FFFFFFF), it indicates that battery temperature sensor is not configured."
            ::= { hwBattsOperate 6 }

        hwBattsAlarmsClear OBJECT-TYPE
            SYNTAX INTEGER
                {
                clearBattTestFailAlm(1),
                clearBattTestCanceledAlm(2),
                clearHighStrImpedanceAlm(3),
                clearHighFloatCurrAlm(4),
                clearCurrImbalanceAlm(5),
                clearContactorFaultAlm(6),
                nullOper(255)
                }
            MAX-ACCESS read-write
            STATUS current
            DESCRIPTION
                "Battery alarms clear. It is an enumeration type:
                  If the enumeration value is 1, it indicates the clear batt test fail alarm ;
                  If the enumeration value is 2, it indicates the clear batt test canceled alarm .
                  If the enumeration value is 3, it indicates the clear high str impedance alarm .
                  If the enumeration value is 4, it indicates the clear high float current alarm .
                  If the enumeration value is 5, it indicates the clear current imbalance alarm .
                  If the enumeration value is 6, it indicates the clear contactor fault alarm .
                  If the enumeration value is 255, it indicates null oper(can't set to smu)."
            ::= { hwBattsOperate 7 }

        hwBattsRatedCapacity OBJECT-TYPE
            SYNTAX Unsigned32 (0..2147483647)
            MAX-ACCESS read-only
            STATUS current
            DESCRIPTION
                "Batteries actual capacity. 
                It is an analog parameter collected by the battery string in real time.
                Value range: 0 to 2147483647, 
                unit: Ah, 
                the value is an integer (1).  
                If the value is 2147483647(0x7FFFFFFF), it indicates that the value is invalid."
            ::= { hwBattsOperate 8 }

        hwBattsRemainCapacity OBJECT-TYPE
            SYNTAX Unsigned32 (0..2147483647)
            MAX-ACCESS read-only
            STATUS current
            DESCRIPTION
                "Remaining capacity of all of the battery. 
                It is an analog parameter collected by the battery string in real time. 
                Value range: 0 to 2147483647, 
                unit: Ah, 
                and the value is an integer (1).  
                If the value is 2147483647(0x7FFFFFFF), it indicates that the value is invalid."
            ::= { hwBattsOperate 9 }

        hwTotalRemainingCapacityPercent OBJECT-TYPE
            SYNTAX Unsigned32 (0..100)
            MAX-ACCESS read-only
            STATUS current
            DESCRIPTION
                "Total Remaining Capacity Percent. 
                Value range: 0 to 100, unit: %, 
                and the value is an integer.(1). 
                If the value is 2147483647(0x7FFFFFFF), it indicates that the value is invalid."
            ::= { hwBattsOperate 10 }

        hwBattsTotalDischargeDepth OBJECT-TYPE
            SYNTAX Unsigned32 (0..100)
            MAX-ACCESS read-only
            STATUS current
            DESCRIPTION
                "Battery Total Discharge Depth Percent. Value range: 0 to 100, unit: %, and the value is an integer. If the value is 2147483647(0x7FFFFFFF), it indicates that the value is invalid."
            ::= { hwBattsOperate 11 }

        hwBatteryAddedCycleTimes OBJECT-TYPE
            SYNTAX Unsigned32 (0..3000000)
            MAX-ACCESS read-only
            STATUS current
            DESCRIPTION
                "Battery added cycle times. Value range: 0 to 3000000, and the value is an integer. If the value is 2147483647(0x7FFFFFFF), it indicates that the value is invalid."
            ::= { hwBattsOperate 13 }

        hwBattsTest OBJECT IDENTIFIER ::= { hwSiteBatterys 3 }

        hwBattsTestRecordCount OBJECT-TYPE
            SYNTAX Unsigned32 (0..100)
            MAX-ACCESS read-only
            STATUS current
            DESCRIPTION
                "Battery test records number."
            ::= { hwBattsTest 1 }

        hwSetBattsManuStdTestTime OBJECT-TYPE
            SYNTAX Unsigned32 (1..6000)
            MAX-ACCESS read-write
            STATUS current
            DESCRIPTION
                "Battery standard test time, It can be configured by users,
                value range defines between 1 to 6000, 
                unit: minutes(min).  
                and its value is an integer (1). 
                Here, if battery manual test is standard mode, 
                If the value is 2147483647(0x7FFFFFFF), it indicates that the value is invalid."
            ::= { hwBattsTest 2 }

        hwSetBattsManuStdTestEndVolt OBJECT-TYPE
            SYNTAX Unsigned32 (170..220)
            MAX-ACCESS read-write
            STATUS current
            DESCRIPTION
                "Test end voltage of single battery, which can be configured by users.
                value range defines between 1.7 to 2.2
                unit: V/cell, 
                and the value is accurate to two decimal place (.01).  
                Here, if battery manual test is standard mode, . If the value is 2147483647(0x7FFFFFFF), it indicates that the value is invalid."
            ::= { hwBattsTest 3 }

        hwSetBattsManuStdTestCellNum OBJECT-TYPE
            SYNTAX Unsigned32 (1..50)
            MAX-ACCESS read-write
            STATUS current
            DESCRIPTION
                "Battery cell number in each Group, which is used in the battery standard manual test, can be configured by users. 
                unit: psc or cell, 
                value range defines between 1 to 50. 
                and value is an integer (1)."
            ::= { hwBattsTest 4 }

        hwSetBattsManuShortTestTime OBJECT-TYPE
            SYNTAX Unsigned32 (1..240)
            MAX-ACCESS read-write
            STATUS current
            DESCRIPTION
                "Battery short test time, It can be configured by users,
                value range defines between 1 to 240,  
                unit: minutes(min).
                and its value is an integer (1).
                If battery manual test is simple mode,  
                If the value is 2147483647(0x7FFFFFFF), it indicates that the value is invalid."
            ::= { hwBattsTest 5 }

        hwSetBattsManuShortTestEndVolt OBJECT-TYPE
            SYNTAX Unsigned32 (442..530)
            MAX-ACCESS read-write
            STATUS current
            DESCRIPTION
                "Voltage when the battery short test is ended, can be configured by users. Here, if battery manual test is standard mode, 
                value range defines between 44.2 to 53, 
                unit: V, 
                and the value is accurate to one decimal place (.1). 
                If the value is 2147483647(0x7FFFFFFF), it indicates that the value is invalid."
            ::= { hwBattsTest 6 }

        hwCtrlBattsTestStartStop OBJECT-TYPE
            SYNTAX INTEGER
                {
                stdTestStart(1),
                shortTestStart(2),
                testStop(3),
                nullOper(255)
                }
            MAX-ACCESS read-write
            STATUS current
            DESCRIPTION
                "Battery manualtest start and stop. It is an enumeration value. 
                  If the value is 1, it means to start a standard manual test; 
                  If the value is 2, it means to start a short manual test; 
                  If the value is 3, it means to stop the battery test.
                If the value is 255, it means null operate(can't set to smu);  
                  Set the parameters, such as battery test time, and voltage when the battery test stops before the node controls the start of the battery test. If the parameters are not set this time, the system uses the configuration parameters by default; and if the battery test is started at the first time, the system uses the default value. 
                  Battery test can only start up in some conditions, so that the reason of Start of battery short test failed may be as follow:
                  1. Interval between this test and the latest AC outage or test is longer than the preset duration.
                  2. No major alarm is raised.
                  3. The number of healthy modules is greater than 0.
                  4. The number of battery strings is greater than 0."
            ::= { hwBattsTest 7 }

        hwBattsTestResultTable OBJECT-TYPE
            SYNTAX SEQUENCE OF HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            ::= { hwBattsTest 100 }

        hwBattsTestResultEntry OBJECT-TYPE
                        SYNTAX HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            INDEX { hwBattsTestResultIndex }
            ::= { hwBattsTestResultTable 1 }

        HwBattsTestResultEntry            ::= SEQUENCE {
                hwBattsTestResultIndex
                    Integer32,
                hwBattsTestType
                    INTEGER,
                hwBattsTestStartTime
                    OCTET STRING,
                hwBattsTestResult
                    INTEGER,
                hwBattsEfficiency
                    Integer32,
                hwBattsDischargeTime
                    Unsigned32,
                hwBattsDischargeEndVoltage
                    Unsigned32,
                hwBattsDischargeAvCurrent
                    Integer32,
                hwBattsDischargeAhValue
                    Unsigned32,
                hwBattsTestTemperature
                    Integer32,
                hwBattsTestEndCourse
                    INTEGER,
                hwBattsTestResultRowStatus
                    RowStatus
            }

        hwBattsTestResultIndex OBJECT-TYPE
            SYNTAX Integer32 (1..100)
            MAX-ACCESS read-only
            STATUS current
            DESCRIPTION
                "Table index of the battery test results. Currently up to 10 times of the battery test results are saved by default. "
            ::= { hwBattsTestResultEntry 1 }

        hwBattsTestType OBJECT-TYPE
            SYNTAX INTEGER
                {
                manualTest(1),
                acOffAutoTest(2),
                timedTest(3),
                shortTest(4),
                unknown(255)
                }
            MAX-ACCESS read-only
            STATUS current
            DESCRIPTION
                "Record test type of the battery test. It is an enumeration value: 
                  If the NMS notifies the SNMP agent that this node is set to 1, it indicates a manual test; 
                  If the NMS notifies the SNMP agent that this node is set to 2, it indicates a simplified test;
                  If the NMS notifies the SNMP agent that this node is set to 3, it indicates a timed test;
                  If the NMS notifies the SNMP agent that this node is set to 4, it indicates a short test;
                  If the NMS notifies the SNMP agent that this node is set to 255, it indicates a other test."
            ::= { hwBattsTestResultEntry 2 }

        hwBattsTestStartTime OBJECT-TYPE
            SYNTAX OCTET STRING (SIZE (0..127))
            MAX-ACCESS read-only
            STATUS current
            DESCRIPTION
                "Test start time of the record in the battery test. It is of the character string type."
            ::= { hwBattsTestResultEntry 3 }

        hwBattsTestResult OBJECT-TYPE
            SYNTAX INTEGER
                {
                battNoResult(1),
                battNormal(2),
                battPreAlarm(3),
                battAlarm(4),
                unknown(255)
                }
            MAX-ACCESS read-only
            STATUS current
            DESCRIPTION
                "Battery test result. It is an enumeration value.
                  If the enumeration value of the node is 1, it indicates that the battery test has no result: 
                  If the enumeration value of the node is 2, it indicates that the battery is in the normal state: 
                  If the enumeration value of the node is 3, it indicates that the battery is in the minor abnormal state, 
                  If the enumeration value of the node is 4, it indicates that the battery is in the alarm state,
                  If the enumeration value of the node is 255, it indicates that the battery state is unknown,"
            ::= { hwBattsTestResultEntry 4 }

        hwBattsEfficiency OBJECT-TYPE
            SYNTAX Integer32 (0..100)
            MAX-ACCESS read-only
            STATUS current
            DESCRIPTION
                "Battery efficiency test. 
                Value range: 0 to 100, 
                unit: %, 
                and the value is an integer (1).
                  If the value is -1, it indicates that the test value is inefficient.
                  If the value is 255, it indicates that the test value is invalid."
            ::= { hwBattsTestResultEntry 5 }

        hwBattsDischargeTime OBJECT-TYPE
            SYNTAX Unsigned32 (0..10000)
            MAX-ACCESS read-only
            STATUS current
            DESCRIPTION
                "Discharge time of the battery test records. 
                Value range: 0 to 100, 
                unit: hour (h), 
                and the value is accurate to two decimal places (.01).  
                If the value is 2147483647(0x7FFFFFFF), it indicates that the value is invalid."
            ::= { hwBattsTestResultEntry 6 }

        hwBattsDischargeEndVoltage OBJECT-TYPE
            SYNTAX Unsigned32 (0..600)
            MAX-ACCESS read-only
            STATUS current
            DESCRIPTION
                "Discharge termination voltage of the battery test. 
                Value range: 0 to 60, 
                unit: V, 
                and the value is accurate to one decimal place (.1).  
                If the value is 2147483647(0x7FFFFFFF), it indicates that the value is invalid."
            ::= { hwBattsTestResultEntry 7 }

        hwBattsDischargeAvCurrent OBJECT-TYPE
            SYNTAX Integer32 ( -10000..10000)
            MAX-ACCESS read-only
            STATUS current
            DESCRIPTION
                "Average discharge current of the battery test. 
                Value range: -1000 to 1000, 
                unit: A, 
                and the value is accurate to one decimal place (.1).  
                If the value is 2147483647(0x7FFFFFFF), it indicates that the value is invalid."
            ::= { hwBattsTestResultEntry 8 }

        hwBattsDischargeAhValue OBJECT-TYPE
            SYNTAX Unsigned32 (0..5000)
            MAX-ACCESS read-only
            STATUS current
            DESCRIPTION
                "Discharge ampere per hour the battery test. 
                Value range: 0 to 5000, 
                unit: Ah, 
                and the value is an integer (1).   
                If the value is 2147483647(0x7FFFFFFF), it indicates that the value is invalid."
            ::= { hwBattsTestResultEntry 9 }

        hwBattsTestTemperature OBJECT-TYPE
            SYNTAX Integer32 ( -50..100)
            MAX-ACCESS read-only
            STATUS current
            DESCRIPTION
                "Battery temperature of the battery test termination. 
                Value range: -50 to +100, 
                unit: centigrade (degC), 
                and the value is an integer (1). 
                If the value is -1024, it indicates that no battery temperature value sensor is detected."
            ::= { hwBattsTestResultEntry 10 }

        hwBattsTestEndCourse OBJECT-TYPE
            SYNTAX INTEGER
                {
                voltageToEnd(1),
                timeToEnd(2),
                acOnToEnd(3),
                manulToEnd(4),
                faultAlarmToEnd(5),
                lowCapacityToEnd(6),
                lowTempToEnd(7),
                unknown(255)
                }
            MAX-ACCESS read-only
            STATUS current
            DESCRIPTION
                "Termination factors of the battery test. It is an enumeration value. 
                  If the enumeration value is 1, it indicates that the voltage value of the battery test reaches the set termination voltage; 
                  If the enumeration value is 2, it indicates that the voltage value of the battery test reaches the timing limit; 
                  If the enumeration value is 3, it indicates that an alarm related to the battery leads to the stop of the battery test; 
                  If the enumeration value is 4, it indicates that a battery test is stopped manually,
                  If the enumeration value is 5, it indicates that battery fault alarm happened,
                If the enumeration value is 6, it indicates that battery low capacity happened,
                If the enumeration value is 7, it indicates that battery low temp happened,
                  If the enumeration value is 255, it indicates that battery test end for other courses."
            ::= { hwBattsTestResultEntry 11 }

        hwBattsTestResultRowStatus OBJECT-TYPE
            SYNTAX RowStatus
            MAX-ACCESS read-create
            STATUS current
            DESCRIPTION
                "RowStatus of battery test table."
            ::= { hwBattsTestResultEntry 100 }

        hwSetBattsConsCurrTestEnable OBJECT-TYPE
            SYNTAX INTEGER
                {
                disable(1),
                enable(2)
                }
            MAX-ACCESS read-write
            STATUS current
            DESCRIPTION
                "Battery constant current test function enable or disable. It is an enumeration value. 
                  If the value is 1, it means the function is disabled; 
                  If the value is 2, it means the function is enabled."
            ::= { hwBattsTest 8 }

        hwSetBattsConsCurrTestDischCurrent OBJECT-TYPE
            SYNTAX Unsigned32 (1..9999)
            MAX-ACCESS read-write
            STATUS current
            DESCRIPTION
                "The battery discharge current in the constant current test. 
                It is an integer value(range:1A~9999A) and the value is accurate to 1A."
            ::= { hwBattsTest 9 }

        hwSetBattsTimeTestMode OBJECT-TYPE
            SYNTAX INTEGER
                {
                disable(1),scheduledTest(2),timeTest(3)
                }
            MAX-ACCESS read-write
            STATUS current
            DESCRIPTION
                "Battery constant current test function enable or disable. 
                It is an enumeration value.
                If the value is 1, it means to disable the test of battery; 
                If the value is 2, it means to enable the Planned Test of battery.
                If the value is 3, it means to enable the Timed Test of battery."
            ::= { hwBattsTest 10 }

        hwSetBattsScheduledTestPeriod OBJECT-TYPE
            SYNTAX Unsigned32 (2..999)
            MAX-ACCESS read-write
            STATUS current
            DESCRIPTION
                "Scheduled Test Period. 
                Value range: 2 to 999, 
                unit: Day, 
                and the value is an integer.(1). 
                If the value is 2147483647(0x7FFFFFFF), it indicates that the value is invalid."
            ::= { hwBattsTest 11 }

        hwSetBattsTestEndCapacity OBJECT-TYPE
            SYNTAX Unsigned32 (0..99)
            MAX-ACCESS read-write
            STATUS current
            DESCRIPTION
                "Test End Capacity.  
                Value range: 0 to 99, 
                unit: %, 
                and the value is an integer. 
                If the value is 2147483647(0x7FFFFFFF), it indicates that the value is invalid."
            ::= { hwBattsTest 12 }

        hwSetBattsTestEndTemperature OBJECT-TYPE
            SYNTAX Integer32 (-5..15)
            MAX-ACCESS read-write
            STATUS current
            DESCRIPTION
                "Test End Temperature. 
                Value range: -5 to 15, 
                unit: degC, 
                and the value is an integer.(1). 
                If the value is 2147483647(0x7FFFFFFF), it indicates that the value is invalid."
            ::= { hwBattsTest 13 }

        hwSetBattsShortTestEnable OBJECT-TYPE
            SYNTAX INTEGER
                {
                disable(1),enable(2)
                }
            MAX-ACCESS read-write
            STATUS current
            DESCRIPTION
                "Battery short test enable.
                It is an enumeration value, and can be configured. 
                If the enumeration value is 1, it indicates battery short test is disabled;
                If the enumeration value is 2, it indicates battery short test is enabled. "
            ::= { hwBattsTest 14 }

        hwSetBattsShortTestPeriod OBJECT-TYPE
            SYNTAX Unsigned32 (1..360)
            MAX-ACCESS read-write
            STATUS current
            DESCRIPTION
                "Short Test Period. 
                Value range: 1 to 360, 
                unit: Day, 
                and the value is an integer.(1). 
                If the value is 2147483647(0x7FFFFFFF), it indicates that the value is invalid."
            ::= { hwBattsTest 15 }

        hwBattString OBJECT IDENTIFIER ::= { hwSiteBatterys 4 }

        hwBattStringConfigTable OBJECT-TYPE
            SYNTAX SEQUENCE OF HwBattStringConfigEntry
            MAX-ACCESS not-accessible
             STATUS current
             DESCRIPTION
                "Battery string config table. Use this table to get battery string equipment ID and equipment name, to set battery standard capacity and battery install time as well. This table's index is hwBattStringConfigIndex, clone battery string config table."
            ::= { hwBattString 1 }

        hwBattStringConfigEntry OBJECT-TYPE
                        SYNTAX HwBattStringConfigEntry
            MAX-ACCESS not-accessible
             STATUS current
             DESCRIPTION
                "Battery string config table. Use this table to get battery string equipment ID and equipment name, to set battery standard capacity and battery install time as well. This table's index is hwBattStringConfigIndex, clone battery string config table."
            INDEX { hwBattStringConfigIndex }
            ::= { hwBattStringConfigTable 1 }

        HwBattStringConfigEntry            ::= SEQUENCE {
                hwBattStringConfigIndex
                    Integer32,
                hwBattStringEquipId
                    Unsigned32,
                hwBattStringEquipName
                    OCTET STRING,
                hwSetBattsTempUpperLimit
                    Integer32,
                hwSetBattsTempLowerLimit
                    Integer32,
                hwSetBattStdCapacity
                    Integer32,
                hwBattStringFatherEquipname
                    OCTET STRING
            }

        hwBattStringConfigIndex OBJECT-TYPE
            SYNTAX Integer32 (1..100)
            MAX-ACCESS read-only
            STATUS current
            DESCRIPTION
                "Device table index of the battery string,
                value range: 1 to 100(To the actual subject)."
            ::= { hwBattStringConfigEntry 1 }

        hwBattStringEquipId OBJECT-TYPE
            SYNTAX Unsigned32 (3001..3100)
            MAX-ACCESS read-only
            STATUS current
            DESCRIPTION
                "Batteries device ID, can be configured by users. 
                Value range: 003,001 to 003,100, in which the first three digits specify the device type and the last three specify the device SN."
            ::= { hwBattStringConfigEntry 2 }

        hwBattStringEquipName OBJECT-TYPE
            SYNTAX OCTET STRING (SIZE (0..63))
            MAX-ACCESS read-only
            STATUS current
            DESCRIPTION
                "Batteries device name, of the character string type, is used to specify the batteries. "
            ::= { hwBattStringConfigEntry 3 }

        hwSetBattsTempUpperLimit OBJECT-TYPE
            SYNTAX Integer32 ( 25..80)
            MAX-ACCESS read-write
            STATUS current
            DESCRIPTION
                "Upper threshold of the battery temperature alarm, can be configured by users. 
                Value range: 25 to 80, 
                unit: centigrade (degC), 
                and the value is an integer (1).  
                If the value is 2147483647(0x7FFFFFFF), it indicates that the value is invalid.
                NOTE: There is linkage between hwSetBattsHTDLimit and hwSetBattsTempUpperLimit"
            ::= { hwBattStringConfigEntry 4 }

        hwSetBattsTempLowerLimit OBJECT-TYPE
            SYNTAX Integer32 ( -20..20)
            MAX-ACCESS read-write
            STATUS current
            DESCRIPTION
                "Lower threshold of the battery temperature alarm, can be configured by users. 
                Value range: -20 to 20, 
                unit: centigrade (degC), 
                and the value is an integer (1).  
                If the value is 2147483647(0x7FFFFFFF), it indicates that the value is invalid."
            ::= { hwBattStringConfigEntry 5 }

        hwSetBattStdCapacity OBJECT-TYPE
            SYNTAX Integer32 (5..12000)
            MAX-ACCESS read-write
            STATUS current
            DESCRIPTION
                "Set battery standard capacity, is an inherent attribute of the device. 
                Value range: 5 to 12000, 
                unit: Ah, 
                the value is an integer (1).   
                If the value is 2147483647(0x7FFFFFFF), it indicates that the value is invalid."
            ::= { hwBattStringConfigEntry 8 }

        hwBattStringFatherEquipname OBJECT-TYPE
            SYNTAX OCTET STRING
            MAX-ACCESS read-only
            STATUS current
            DESCRIPTION
                "Name of the parent device of the Batteries"
            ::= { hwBattStringConfigEntry 10 }

        hwBattStringOperTable OBJECT-TYPE
            SYNTAX SEQUENCE OF HwBattStringOperEntry
            MAX-ACCESS not-accessible
             STATUS current
             DESCRIPTION
                "Battery string runing table. 
                Use this table to get battery string current, persent of remain capacity, battery remain capacity, battery actual capacity, as well as  battery temperature. 
                This table's index is hwBattStringRunIndex, clone battery string runing table."
            ::= { hwBattString 2 }

        hwBattStringOperEntry OBJECT-TYPE
                        SYNTAX HwBattStringOperEntry
            MAX-ACCESS not-accessible
             STATUS current
             DESCRIPTION
                "Battery string runing table. 
                Use this table to get battery string current, persent of remain capacity, battery remain capacity, battery actual capacity, as well as  battery temperature. 
                This table's index is hwBattStringRunIndex, clone battery string runing table."
            INDEX { hwBattStringOperIndex }
            ::= { hwBattStringOperTable 1 }

        HwBattStringOperEntry            ::= SEQUENCE {
                hwBattStringOperIndex
                    Integer32,
                hwBattStringCurrent
                    Integer32,
                hwBattStringRemainCapacityPercent
                    Unsigned32,
                hwBattStringRemainCapacity
                    Unsigned32,
                hwBattStringTemprature
                    Integer32,
                hwBattStringMidpointVoltage
                    Integer32,
                hwBattStringOperStatus
                    INTEGER
            }

        hwBattStringOperIndex OBJECT-TYPE
            SYNTAX Integer32 (1..100)
            MAX-ACCESS read-only
            STATUS current
            DESCRIPTION
                "Device table index of the battery string, 
                which value range: 1 to 100(To the actual subject)."
            ::= { hwBattStringOperEntry 1 }

        hwBattStringCurrent OBJECT-TYPE
            SYNTAX Integer32 ( -10000..10000)
            MAX-ACCESS read-only
            STATUS current
            DESCRIPTION
                "Batteries current. It is an analog parameter collected by the battery string in real time. 
                Value range: -1000 to +1000, 
                unit: A, 
                and the value is accurate to one decimal place (.1).  
                If the value is 2147483647(0x7FFFFFFF), it indicates that the value is invalid."
            ::= { hwBattStringOperEntry 2 }

        hwBattStringRemainCapacityPercent OBJECT-TYPE
            SYNTAX Unsigned32 (0..100)
            MAX-ACCESS read-only
            STATUS current
            DESCRIPTION
                "Remaining capacity percentage of the battery string. 
                Value range: 0 to 100, 
                unit: %, 
                and the value is an integer (1).  
                If the value is 2147483647(0x7FFFFFFF), it indicates that the value is invalid."
            ::= { hwBattStringOperEntry 3 }

        hwBattStringRemainCapacity OBJECT-TYPE
            SYNTAX Unsigned32 (0..12000)
            MAX-ACCESS read-only
            STATUS current
            DESCRIPTION
                "Remaining capacity of the battery string. It is an analog parameter collected by the battery string in real time. 
                Value range: 0 to 12000, 
                unit: Ah, 
                and the value is an integer (1).  
                If the value is 2147483647(0x7FFFFFFF), it indicates that the value is invalid."
            ::= { hwBattStringOperEntry 4 }

        hwBattStringTemprature OBJECT-TYPE
            SYNTAX Integer32 ( -3000..2000)
            MAX-ACCESS read-only
            STATUS current
            DESCRIPTION
                "Battery temperature. It is a battery parameter collected in real time. 
                Value range: -300 to +200, 
                unit: centigrade (degC), 
                and the value is accurate to one decimal place (.1).
                If the value is 2147483647(0x7FFFFFFF), it indicates that battery temperature sensor is not configured."
            ::= { hwBattStringOperEntry 6 }

        hwBattStringMidpointVoltage OBJECT-TYPE
            SYNTAX Integer32 ( -900..900)
            MAX-ACCESS read-only
            STATUS current
            DESCRIPTION
                "Batteries midpoint voltage. It is an analog parameter collected by the battery string in real time. 
                Value range: -90 to +90, 
                unit: V, 
                and the value is accurate to one decimal place (.1)."
            ::= { hwBattStringOperEntry 7 }

        hwBattStringOperStatus OBJECT-TYPE
            SYNTAX INTEGER
                {
                normal(1),
                tempHigh(2),
                tempLow(3),
                loopBreak(4),
                overCurrent(5),
                unbalance(6),
                discharge(7),
                fuseBreak(8),
                alarmResume(254),
                unknown(255)
                }
            MAX-ACCESS read-only
            STATUS current
            DESCRIPTION
                "State of the site battery string module. It is an enumeration type: 
                  If the enumeration value is 1, it indicates that the site battery string is in the normal state; 
                  If the enumeration value is 2, it indicates that the battery string is over upper alarm threshold of temperature; 
                  If the enumeration value is 3, it indicates that the battery string is under lower alarm threshold of temperature;  
                  If the enumeration value is 4, it indicates that battery string loop has disconnected;  
                  If the enumeration value is 5, it indicates that the current of batery is over upper charging threshold;
                  If the enumeration value is 6, it indicates that the battery string is unbalance;  
                  If the enumeration value is 7, it indicates that battery string is discharge;  
                  If the enumeration value is 8, it indicates that battery string is fuseBreak;
                  If the enumeration value is 254, it indicates battery string alarm resume; 
                  If the enumeration value is 255, it indicates battery string operation status unknown. "
            ::= { hwBattStringOperEntry 99 }

        hwSiteAcDistributions OBJECT IDENTIFIER ::= { hwSiteMonitorMIBObjects 5 }

        hwAcDistributionsGroup OBJECT IDENTIFIER ::= { hwSiteAcDistributions 1 }

        hwAcsGroupId OBJECT-TYPE
            SYNTAX Unsigned32
            MAX-ACCESS read-only
            STATUS current
            DESCRIPTION
                "AC group ID, is the unique ID of the AC group. The first three digits indicate the device type and the last three indicate the device SN. If the last three digits are 000, it indicates a virtual device. "
            ::= { hwAcDistributionsGroup 1 }

        hwAcsGroupName OBJECT-TYPE
            SYNTAX OCTET STRING (SIZE (0..63))
            MAX-ACCESS read-only
            STATUS current
            DESCRIPTION
                "Device name of the AC group. It is of the character string type, and can be configured by users. Otherwise, the configured character can not be any other languages except English."
            ::= { hwAcDistributionsGroup 2 }

        hwAcsTotalCurrent OBJECT-TYPE
            SYNTAX Unsigned32 (0..300000)
            MAX-ACCESS read-only
            STATUS current
            DESCRIPTION
                "Total current of the AC group. It indicates the real-time statistics of the AC group. 
                Value range: 0 to 30000, 
                unit: A, 
                and the value is accurate to one decimal place (.1). 
                If the value is 2147483647(0x7FFFFFFF), it indicates that the value is invalid."
            ::= { hwAcDistributionsGroup 3 }

        hwAcsInputQuantity OBJECT-TYPE
            SYNTAX Unsigned32 (0..100)
            MAX-ACCESS read-only
            STATUS current
            DESCRIPTION
                "Total quantity of the site ACUs. Value range: 0 to 100. "
            ::= { hwAcDistributionsGroup 4 }

        hwSetAcsUpperVoltLimit OBJECT-TYPE
            SYNTAX Unsigned32 (50..600)
            MAX-ACCESS read-write
            STATUS current
            DESCRIPTION
                "Upper threshold of the AC voltage alarm, can be configured by users. 
                Value range: 50 to 600, 
                unit: V, 
                and the value is an integer (1).  
                If the value is 2147483647(0x7FFFFFFF), it indicates that the value is invalid.
                NOTE: There is linkage between hwSetAcsUpperVoltLimit and hwSetAcsLowerVoltLimit"
            ::= { hwAcDistributionsGroup 5 }

        hwSetAcsLowerVoltLimit OBJECT-TYPE
            SYNTAX Unsigned32 (50..600)
            MAX-ACCESS read-write
            STATUS current
            DESCRIPTION
                "Lower threshold of the AC voltage alarm, can be configured by users. 
                Value range: 50 to 600, 
                unit: V, 
                and the value is an integer (1).  
                If the value is 2147483647(0x7FFFFFFF), it indicates that the value is invalid.
                NOTE: There is linkage between hwSetAcsUpperVoltLimit and hwSetAcsLowerVoltLimit"
            ::= { hwAcDistributionsGroup 6 }

        hwAcsPowerConsumption OBJECT-TYPE
            SYNTAX Unsigned32 (0..4294967295)
            MAX-ACCESS read-only
            STATUS current
            DESCRIPTION
                "Low 32bits of AC Active power Consumption. Value range:0 to 4294967295, resolution 10wh.
                If GET value is 10, it means  the real consumption is 10*10wh = 100wh (0.1kwh)"
            ::= { hwAcDistributionsGroup 7 }

        hwAcsReactivePowerConsumption OBJECT-TYPE
            SYNTAX Unsigned32 (0..4294967295)
            MAX-ACCESS read-only
            STATUS current
            DESCRIPTION
                "Low 32bits of AC Reactive Power Consumption. Value range:0 to 4294967295, resolution 10varh.
                If GET value is 10, it means  the real consumption is 10*10varh = 100varh (0.1kvarh)"
            ::= { hwAcDistributionsGroup 9 }

        hwAcsReactivePowerConsumptionHigh32b OBJECT-TYPE
            SYNTAX Unsigned32 (0..4294967295)
            MAX-ACCESS read-only
            STATUS current
            DESCRIPTION
                "High 32bits of AC Reactive Power Consumption. Value range:0 to 4294967295, resolution 10varh."
            ::= { hwAcDistributionsGroup 10 }

        hwAcsActivePowerConsumptionKw OBJECT-TYPE
            SYNTAX Unsigned32 (0..4294967295)
            MAX-ACCESS read-only
            STATUS current
            DESCRIPTION
                "AC Active Power Consumption. Value range:0 to 4294967295, resolution 1kwh."
            ::= { hwAcDistributionsGroup 11 }

        hwAcsReactivePowerConsumptionKvar OBJECT-TYPE
            SYNTAX Unsigned32 (0..4294967295)
            MAX-ACCESS read-only
            STATUS current
            DESCRIPTION
                "AC Reactive Power Consumption. Value range:0 to 4294967295, resolution 1kwh."
            ::= { hwAcDistributionsGroup 12 }

        hwAcsPowerConsumptionHigh32b OBJECT-TYPE
            SYNTAX Unsigned32 (0..4294967295)
            MAX-ACCESS read-only
            STATUS current
            DESCRIPTION
                "High 32bits of AC Active Power Consumption. Value range:0 to 4294967295, resolution 10wh."
            ::= { hwAcDistributionsGroup 8 }

        hwAcDistribution OBJECT IDENTIFIER ::= { hwSiteAcDistributions 2 }

        hwAcInputTable OBJECT-TYPE
            SYNTAX SEQUENCE OF HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            ::= { hwAcDistribution 1 }

        hwAcInputEntry OBJECT-TYPE
                        SYNTAX HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            INDEX { hwAcInputIndex }
            ::= { hwAcInputTable 1 }

        HwAcInputEntry            ::= SEQUENCE {
                hwAcInputIndex
                    Integer32,
                hwAcEquipId
                    Unsigned32,
                hwAcEquipName
                    OCTET STRING,
                hwApOrAblVoltage
                    Unsigned32,
                hwBpOrBclVoltage
                    Unsigned32,
                hwCpOrCalVoltage
                    Unsigned32,
                hwAphaseCurrent
                    Integer32,
                hwBphaseCurrent
                    Integer32,
                hwCphaseCurrent
                    Integer32,
                hwAcInputBreakersQuantity
                    Unsigned32,
                hwSetAcUpperVoltLimit
                    Unsigned32,
                hwSetAcLowerVoltLimit
                    Unsigned32,
                hwAcFatherEquipname
                    OCTET STRING,
                hwAcPowerFactor
                    Integer32,
                hwAcPhaseL1PowerFactor
                    Integer32,
                hwAcPhaseL2PowerFactor
                    Integer32,
                hwAcPhaseL3PowerFactor
                    Integer32,
                hwAcActivePower
                    Unsigned32,
                hwAcReactivePower
                    Integer32,
                hwAcApparentPower
                    Unsigned32,
                hwAcPowerConsumptionReadings
                    Unsigned32,
                hwAcTotalACEnergyConsumption
                    Unsigned32,
                hwAcDistriAcFrequency
                    Unsigned32,
                hwAcInputOperStatus
                    INTEGER,
                hwAcRowStatus
                    RowStatus
            }

        hwAcInputIndex OBJECT-TYPE
            SYNTAX Integer32 (1..100)
            MAX-ACCESS read-only
            STATUS current
            DESCRIPTION
                "ACU device table index, 
                which value range: 1 to 100. 
                Lines of the device list are restricted by the total quantity of ACUs (hwAcsInputQuantity)."
            ::= { hwAcInputEntry 1 }

        hwAcEquipId OBJECT-TYPE
            SYNTAX Unsigned32
            MAX-ACCESS read-only
            STATUS current
            DESCRIPTION
                "ACU device ID. Value range: 004,001 to 004,100, 
                in which The first digits indicate the device type and the last three digits indicate the device SN."
            ::= { hwAcInputEntry 2 }

        hwAcEquipName OBJECT-TYPE
            SYNTAX OCTET STRING (SIZE (0..63))
            MAX-ACCESS read-only
            STATUS current
            DESCRIPTION
                "ACU device name, of the character string type, is used to specify the alternating current unit (ACU). 
                "
            ::= { hwAcInputEntry 3 }

        hwApOrAblVoltage OBJECT-TYPE
            SYNTAX Unsigned32 (0..8000)
            MAX-ACCESS read-only
            STATUS current
            DESCRIPTION
                "ACU A-phase or AB-line voltage. 
                Value range: 0 to 800, 
                unit: V, 
                and the value is accurate to one decimal place (.1).  
                If the value is 2147483647(0x7FFFFFFF), it indicates that the value is invalid."
            ::= { hwAcInputEntry 4 }

        hwBpOrBclVoltage OBJECT-TYPE
            SYNTAX Unsigned32 (0..8000)
            MAX-ACCESS read-only
            STATUS current
            DESCRIPTION
                "ACU B-phase or BC-line voltage. 
                Value range: 0 to 800, 
                unit: V, 
                and the value is accurate to one decimal place (.1).  
                If the value is 2147483647(0x7FFFFFFF), it indicates that the value is invalid."
            ::= { hwAcInputEntry 5 }

        hwCpOrCalVoltage OBJECT-TYPE
            SYNTAX Unsigned32 (0..8000)
            MAX-ACCESS read-only
            STATUS current
            DESCRIPTION
                "ACU C-phase or CA-line voltage. 
                Value range: 0 to 800, 
                unit: V, 
                and the value is accurate to one decimal place (.1).  
                If the value is 2147483647(0x7FFFFFFF), it indicates that the value is invalid."
            ::= { hwAcInputEntry 6 }

        hwAphaseCurrent OBJECT-TYPE
            SYNTAX Integer32 (0..200000)
            MAX-ACCESS read-only
            STATUS current
            DESCRIPTION
                "ACU A-phase current. It is an analog parameter collected by the ACU in real time. 
                Value range: 0 to 20000, 
                unit: A, 
                and the value is accurate to one decimal place (.1).  
                If the value is 2147483647(0x7FFFFFFF), it indicates that the value is invalid."
            ::= { hwAcInputEntry 7 }

        hwBphaseCurrent OBJECT-TYPE
            SYNTAX Integer32 (0..200000)
            MAX-ACCESS read-only
            STATUS current
            DESCRIPTION
                "ACU B-phase current. It is an analog parameter collected by the ACU in real time. 
                Value range: 0 to 20000, 
                unit: A, 
                and the value is accurate to one decimal place (.1). 
                If the value is 2147483647(0x7FFFFFFF), it indicates that the value is invalid."
            ::= { hwAcInputEntry 8 }

        hwCphaseCurrent OBJECT-TYPE
            SYNTAX Integer32 (0..200000)
            MAX-ACCESS read-only
            STATUS current
            DESCRIPTION
                "ACU C-phase current. It is an analog parameter collected by the ACU in real time. 
                Value range: 0 to 20000, 
                unit: A, 
                and the value is accurate to one decimal place (.1).  
                If the value is 2147483647(0x7FFFFFFF), it indicates that the value is invalid."
            ::= { hwAcInputEntry 9 }

        hwAcInputBreakersQuantity OBJECT-TYPE
            SYNTAX Unsigned32 (0..100)
            MAX-ACCESS read-only
            STATUS current
            DESCRIPTION
                "Quantity of the AC air circuit breakers. 
                As the ACU lower-level subset, the node indicates the quantity of the output air circuit breakers contained by each ACU lower-level subset. Value range: 0 to 100. "
            ::= { hwAcInputEntry 10 }

        hwSetAcUpperVoltLimit OBJECT-TYPE
            SYNTAX Unsigned32 (0..1000)
            MAX-ACCESS read-write
            STATUS current
            DESCRIPTION
                "Upper threshold of the AC line voltage alarm, can be configured by users. 
                Value range: 60 to 600, 
                unit: V, 
                and the value is an integer (1).  
                Upper threshold of the AC phase voltage alarm, can be configured by users. 
                Value range: 60 to 300, 
                unit: V, 
                and the value is an integer (1).  
                If the value is 2147483647(0x7FFFFFFF), it indicates that the value is invalid.
                NOTE: There is linkage between hwSetAcsUpperVoltLimit and hwSetAcsLowerVoltLimit.
                If the normal value setting fails, it means that the setting value is not within the support range.
                In addition, AC Mode can be configured in Mains - Running parameters."
            ::= { hwAcInputEntry 11 }

        hwSetAcLowerVoltLimit OBJECT-TYPE
            SYNTAX Unsigned32 (0..1000)
            MAX-ACCESS read-write
            STATUS current
            DESCRIPTION
                "Lower threshold of the AC line voltage alarm, can be configured by users. 
                Value range: 60 to 600, 
                unit: V, 
                and the value is an integer (1).  
                Lower threshold of the AC phase voltage alarm, can be configured by users. 
                Value range: 60 to 300, 
                unit: V, 
                and the value is an integer (1).  
                If the value is 2147483647(0x7FFFFFFF), it indicates that the value is invalid.
                NOTE: There is linkage between hwSetAcsUpperVoltLimit and hwSetAcsLowerVoltLimit.
                If the normal value setting fails, it means that the setting value is not within the support range.
                In addition, AC Mode can be configured in Mains - Running parameters."
            ::= { hwAcInputEntry 12 }

        hwAcFatherEquipname OBJECT-TYPE
            SYNTAX OCTET STRING
            MAX-ACCESS read-only
            STATUS current
            DESCRIPTION
                "Name of the parent device of the AC"
            ::= { hwAcInputEntry 13 }

        hwAcPowerFactor OBJECT-TYPE
            SYNTAX Integer32 ( -100..100)
            MAX-ACCESS read-only
            STATUS current
            DESCRIPTION
                "Power factor of the Inverter ACU. It is a real-time analog parameter. Value range: -1 to 1, unit: NA, the value is accurate to three decimal place (.01). If the value is 2147483647(0x7FFFFFFF), it indicates that the value is invalid."
            ::= { hwAcInputEntry 14 }

        hwAcPhaseL1PowerFactor OBJECT-TYPE
            SYNTAX Integer32 ( -100..100)
            MAX-ACCESS read-only
            STATUS current
            DESCRIPTION
                "L1 Phase power factor of the ACU. It is a real-time analog parameter. Value range: -1 to 1, unit: NA, the value is accurate to two decimal place (.01). If the value is 2147483647(0x7FFFFFFF), it indicates that the value is invalid.."
            ::= { hwAcInputEntry 15 }

        hwAcPhaseL2PowerFactor OBJECT-TYPE
            SYNTAX Integer32 ( -100..100)
            MAX-ACCESS read-only
            STATUS current
            DESCRIPTION
                "L2 Phase power factor of the ACU. It is a real-time analog parameter. Value range: -1 to 1, unit: NA, the value is accurate to two decimal place (.01). If the value is 2147483647(0x7FFFFFFF), it indicates that the value is invalid.."
            ::= { hwAcInputEntry 16 }

        hwAcPhaseL3PowerFactor OBJECT-TYPE
            SYNTAX Integer32 ( -100..100)
            MAX-ACCESS read-only
            STATUS current
            DESCRIPTION
                "L3 Phase power factor of the ACU. It is a real-time analog parameter. Value range: -1 to 1, unit: NA, the value is accurate to two decimal place (.01). If the value is 2147483647(0x7FFFFFFF), it indicates that the value is invalid.."
            ::= { hwAcInputEntry 17 }

        hwAcActivePower OBJECT-TYPE
            SYNTAX Unsigned32 (0..48000)
            MAX-ACCESS read-only
            STATUS current
            DESCRIPTION
                "Active power of the ACU. It is a real-time analog parameter. Value range: 0 to 480, unit: kW, the value is accurate to two decimal place (.01). If the value is 2147483647(0x7FFFFFFF), it indicates that the value is invalid."
            ::= { hwAcInputEntry 18 }

        hwAcReactivePower OBJECT-TYPE
            SYNTAX Integer32 ( -48000..48000)
            MAX-ACCESS read-only
            STATUS current
            DESCRIPTION
                "Reactive power of the ACU. It is a real-time analog parameter. Value range: -480 to 480, unit: kVA, the value is accurate to two decimal place (.01). If the value is 2147483647(0x7FFFFFFF), it indicates that the value is invalid."
            ::= { hwAcInputEntry 19 }

        hwAcApparentPower OBJECT-TYPE
            SYNTAX Unsigned32 (0..48000)
            MAX-ACCESS read-only
            STATUS current
            DESCRIPTION
                "Apparent power of the ACU. It is a real-time analog parameter. Value range: 0 to 480, unit: kVA, the value is accurate to two decimal place (.01). If the value is 2147483647(0x7FFFFFFF), it indicates that the value is invalid."
            ::= { hwAcInputEntry 20 }

        hwAcPowerConsumptionReadings OBJECT-TYPE
            SYNTAX Unsigned32 (0..99999999)
            MAX-ACCESS read-only
            STATUS current
            DESCRIPTION
                "AC power Consumption. Value range:0 to 999999, resolution 10wh.
                If GET value is 10, it means  the real consumption is 10*10wh = 100wh (0.1kwh)"
            ::= { hwAcInputEntry 21 }

        hwAcTotalACEnergyConsumption OBJECT-TYPE
            SYNTAX Unsigned32 (0..4294967295)
            MAX-ACCESS read-only
            STATUS current
            DESCRIPTION
                "AC power Consumption. Value range:0 to 4294967295, resolution 10wh.
                If GET value is 10, it means  the real consumption is 10*10wh = 100wh (0.1kwh)"
            ::= { hwAcInputEntry 22 }

        hwAcDistriAcFrequency OBJECT-TYPE
            SYNTAX Unsigned32 (0..1000)
            MAX-ACCESS read-only
            STATUS current
            DESCRIPTION
                "AC frequency.Value range: 0 to 100, unit: Hz."
            ::= { hwAcInputEntry 23 }

        hwAcInputOperStatus OBJECT-TYPE
            SYNTAX INTEGER
                {
                normal(1),
                acOff(2),
                acAbsent(3),
                voltHigh(4),
                voltLow(5),
                freqHigh(6),
                freqLow(7),
                alarmResume(254),
                unknown(255)
                }
            MAX-ACCESS read-only
            STATUS current
            DESCRIPTION
                "State of the site AC distribution uint. It is an enumeration type: 
                  If the enumeration value is 1, it indicates that the site AC distribution uint is in the normal state; 
                  If the enumeration value is 2, it indicates that AC distribution uint power off; 
                  If the enumeration value is 3, it indicates that AC input phase absent;
                  If the enumeration value is 4, it indicates that AC voltage is over upper alarm threshold;  
                  If the enumeration value is 5, it indicates that AC voltage is under lower alarm threshold;  
                  If the enumeration value is 6, it indicates that AC voltage is freqHigh;  
                  If the enumeration value is 7, it indicates that AC voltage is freqLow;  
                  If the enumeration value is 254, it indicates AC distribution uint alarm resume; 
                  If the enumeration value is 255, it indicates AC distribution uint operation status unknown. "
            ::= { hwAcInputEntry 99 }

        hwAcRowStatus OBJECT-TYPE
            SYNTAX RowStatus
            MAX-ACCESS read-create
            STATUS current
            DESCRIPTION
                "RowStatus of ACU."
            ::= { hwAcInputEntry 100 }

        hwAcInputBreakerTable OBJECT-TYPE
            SYNTAX SEQUENCE OF HwAcInputBreakerEntry
            MAX-ACCESS not-accessible
             STATUS current
             DESCRIPTION
                "Ac input breaker table. Use this table to get AC input breaker equipment ID, AC input breaker equipment name, and AC input breaker status. This table's index is hwAcInputBreakerIndex, which qualificated by hwAcInputBreakersQuantity in hwAcInputTable, clone Ac input breaker table."
            ::= { hwAcDistribution 2 }

        hwAcInputBreakerEntry OBJECT-TYPE
                        SYNTAX HwAcInputBreakerEntry
            MAX-ACCESS not-accessible
             STATUS current
             DESCRIPTION
                "Ac input breaker table. Use this table to get AC input breaker equipment ID, AC input breaker equipment name, and AC input breaker status. This table's index is hwAcInputBreakerIndex, which qualificated by hwAcInputBreakersQuantity in hwAcInputTable, clone Ac input breaker table."
            INDEX { hwAcInputBreakerIndex }
            ::= { hwAcInputBreakerTable 1 }

        HwAcInputBreakerEntry            ::= SEQUENCE {
                hwAcInputBreakerIndex
                    Integer32,
                hwAcInputBreakerEquipId
                    Unsigned32,
                hwAcInputBreakerEquipName
                    OCTET STRING,
                hwAcInputBreakerOperStatus
                    INTEGER,
                hwAcInputBreakerRowStatus
                    RowStatus
            }

        hwAcInputBreakerIndex OBJECT-TYPE
            SYNTAX Integer32 (1..100)
            MAX-ACCESS read-only
            STATUS current
            DESCRIPTION
                "Device table index of the AC air circuit breaker. 
                Value range: 1 to 100. 
                An input air circuit breaker device can be uniquely identified through the ACU table index and device index of the AC air circuit breaker.  "
            ::= { hwAcInputBreakerEntry 1 }

        hwAcInputBreakerEquipId OBJECT-TYPE
            SYNTAX Unsigned32 (5001..5100)
            MAX-ACCESS read-only
            STATUS current
            DESCRIPTION
                "AC input air circuit breaker ID. 
                Value range: 005,001 to 005,100. 
                The first digits indicate the device type and the last three digits indicate the device SN."
            ::= { hwAcInputBreakerEntry 2 }

        hwAcInputBreakerEquipName OBJECT-TYPE
            SYNTAX OCTET STRING (SIZE (0..63))
            MAX-ACCESS read-write
            STATUS current
            DESCRIPTION
                "AC input air circuit breaker name, of the character string type, can configured by users. Otherwise, the configured character can not be any other languages except English."
            ::= { hwAcInputBreakerEntry 3 }

        hwAcInputBreakerOperStatus OBJECT-TYPE
            SYNTAX INTEGER
                {
                normal(1),
                disconnect(2),
                alarmResume(254),
                unknown(255)
                }
            MAX-ACCESS read-only
            STATUS current
            DESCRIPTION
                "Operation state of the site AC input breaker. It is an enumeration type: 
                  If the enumeration value is 1, it indicates that the site AC input breaker is in the normal state; 
                  If the enumeration value is 2, it indicates that the AC input breaker disconnect; 
                  If the enumeration value is 254, it indicates AC input breaker alarm resume; 
                  If the enumeration value is 255, it indicates AC input breaker operation status unknown. "
            ::= { hwAcInputBreakerEntry 99 }

        hwAcInputBreakerRowStatus OBJECT-TYPE
            SYNTAX RowStatus
            MAX-ACCESS read-create
            STATUS current
            DESCRIPTION
                "RowStatus of AC input breaker."
            ::= { hwAcInputBreakerEntry 100 }

        hwSiteDcDistributions OBJECT IDENTIFIER ::= { hwSiteMonitorMIBObjects 6 }

        hwDcDistributionsGroup OBJECT IDENTIFIER ::= { hwSiteDcDistributions 1 }

        hwDcsGroupId OBJECT-TYPE
            SYNTAX Unsigned32
            MAX-ACCESS read-only
            STATUS current
            DESCRIPTION
                "DC group ID: unique ID of the DC group. in which The first digits indicate the device type and the last three digits indicate the device SN. If the last three digits are 000, it indicates a virtual device."
            ::= { hwDcDistributionsGroup 1 }

        hwDcsGroupName OBJECT-TYPE
            SYNTAX OCTET STRING (SIZE (0..63))
            MAX-ACCESS read-write
            STATUS current
            DESCRIPTION
                "Device name of the DC group, of the character string type, can be configured by users. Otherwise, the configured character can not be any other languages except English."
            ::= { hwDcDistributionsGroup 2 }

        hwDcsTotalVoltage OBJECT-TYPE
            SYNTAX Unsigned32 (0..1000)
            MAX-ACCESS read-only
            STATUS current
            DESCRIPTION
                "Total voltage of the DC group. 
                Value range: 0 to 100, 
                unit: V, 
                and the value is accurate to one decimal place (.1).  
                If the value is 2147483647(0x7FFFFFFF), it indicates that the value is invalid."
            ::= { hwDcDistributionsGroup 3 }

        hwDcsTotalCurrent OBJECT-TYPE
            SYNTAX Integer32 (0..300000)
            MAX-ACCESS read-only
            STATUS current
            DESCRIPTION
                "Total current of the DC group. 
                Value range: 0.0 to 30000.0, 
                unit: A, 
                and the value is accurate to one decimal place (.1).   
                If the value is 2147483647(0x7FFFFFFF), it indicates that the value is invalid."
            ::= { hwDcDistributionsGroup 4 }

        hwDcsTotalPower OBJECT-TYPE
            SYNTAX Unsigned32 (0..3000000)
            MAX-ACCESS read-only
            STATUS current
            DESCRIPTION
                "Total power of the DC group. 
                Value range: 0 to 3000000, 
                unit: W, 
                and the value is an integer (1).  
                If the value is 2147483647(0x7FFFFFFF), it indicates that the value is invalid."
            ::= { hwDcDistributionsGroup 5 }

        hwDcsTotalQuantity OBJECT-TYPE
            SYNTAX Unsigned32 (0..100)
            MAX-ACCESS read-only
            STATUS current
            DESCRIPTION
                "Total quantity of the DC units, and its Value range: 0 to 100."
            ::= { hwDcDistributionsGroup 6 }

        hwSetDcsUpperVoltLimit OBJECT-TYPE
            SYNTAX Unsigned32 (530..600)
            MAX-ACCESS read-write
            STATUS current
            DESCRIPTION
                "Upper threshold of the DC voltage alarm, can be configued by users. 
                Value range: 53 to 60, 
                unit: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 7 }

        hwSetDcsLowerVoltLimit OBJECT-TYPE
            SYNTAX Unsigned32 (360..570)
            MAX-ACCESS read-write
            STATUS current
            DESCRIPTION
                "Lower threshold of the DC voltage alarm, can be configued by users. 
                Value range: 36 to 57, 
                unit: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 8 }

        hwDcsPerfoLoadConsume OBJECT-TYPE
            SYNTAX Unsigned32 (0..429467295)
            MAX-ACCESS read-only
            STATUS current
            DESCRIPTION
                "PerfoLoad Consume of the DC,
                Value range:  0 to 429467295, 
                unit: KWh, 
                and the value is an integer (1).
                If the value is 2147483647(0x7FFFFFFF), it indicates that the value is invalid."
            ::= { hwDcDistributionsGroup 9 }

        hwDcLoadFuseStatus OBJECT-TYPE
            SYNTAX INTEGER
                {
                normal(1),
                disconnect(2),
                unknown(255)
                }
            MAX-ACCESS read-only
            STATUS current
            DESCRIPTION
                "State of the site load output branch. It is an enumeration type: 
                If the enumeration value is 1, it indicates that the site load output branch is in the normal state; 
                If the enumeration value is 2, it indicates that the load output branch disconnect;
                If the enumeration value is 255, it indicates load output branch operation status unknown. "
            ::= { hwDcDistributionsGroup 14 }

        hwSetDcsUltraOverVoltThreshold OBJECT-TYPE
            SYNTAX Unsigned32 (530..600)
            MAX-ACCESS read-write
            STATUS current
            DESCRIPTION
                "DC voltage Ultra High alarm threshold can be configued by users. Value range: 53 to 60, unit: V, and the value is accurate to one decimal space (.1).  If the value is 2147483647(0x7FFFFFFF), it indicates that the value is invalid.
                NOTE: There is linkage between hwSetDcsUpperVoltLimit and hwSetDcsUltraOverVoltThreshold"
            ::= { hwDcDistributionsGroup 10 }

        hwSetDcsUltraUnderVoltThreshold OBJECT-TYPE
            SYNTAX Unsigned32 (360..560)
            MAX-ACCESS read-write
            STATUS current
            DESCRIPTION
                "DC voltage Ultra Low alarm threshold can be configued by users. Value range: 36 to 56, unit: V, and the value is accurate to one decimal space (.1).  If the value is 2147483647(0x7FFFFFFF), it indicates that the value is invalid.
                NOTE: There is linkage between hwSetDcsUltraUnderVoltThreshold and hwSetDcsLowerVoltLimit"
            ::= { hwDcDistributionsGroup 11 }

        hwDcDistribution OBJECT IDENTIFIER ::= { hwSiteDcDistributions 2 }

        hwDcOutputTable OBJECT-TYPE
            SYNTAX SEQUENCE OF HwDcOutputEntry
            MAX-ACCESS not-accessible
             STATUS current
             DESCRIPTION
                "/"
            ::= { hwDcDistribution 1 }

        hwDcOutputEntry OBJECT-TYPE
                        SYNTAX HwDcOutputEntry
            MAX-ACCESS not-accessible
             STATUS current
             DESCRIPTION
                "/"
            INDEX { hwDcOutputIndex }
            ::= { hwDcOutputTable 1 }

        HwDcOutputEntry            ::= SEQUENCE {
                hwDcOutputIndex
                    Integer32,
                hwDcOutputEquipId
                    Unsigned32,
                hwDcOutputEquipName
                    OCTET STRING,
                hwDcOutputVoltage
                    Unsigned32,
                hwDcOutputCurrent
                    Integer32,
                hwDcOutputPower
                    Unsigned32,
                hwLoadsQuantity
                    Unsigned32,
                hwLoadUsage
                    Unsigned32,
                hwSetDcUpperVoltLimit
                    Unsigned32,
                hwSetDcLowerVoltLimit
                    Unsigned32,
                hwDcFatherEquipname
                    OCTET STRING,
                hwTotalDcLoadEnergyConsumption
                    Unsigned32,
                hwDcDistriIcbdNum
                    Unsigned32,
                hwDcDistriCommNormalIcbdNum
                    Unsigned32,
                hwDcDistriLoadFuseStatus1
                    Unsigned32,
                hwDcDistriLoadFuseStatus2
                    Unsigned32,
                hwDcOutputOperStatus
                    INTEGER,
                hwDcOutputRowStatus
                    RowStatus
            }

        hwDcOutputIndex OBJECT-TYPE
            SYNTAX Integer32 (1..65535)
            MAX-ACCESS read-only
            STATUS current
            DESCRIPTION
                "Device table index of the DC units, which value range: 1 to 65535. Lines of the device list are restricted by the total quantity of DC units (hwDcsQuantity)."
            ::= { hwDcOutputEntry 1 }

        hwDcOutputEquipId OBJECT-TYPE
            SYNTAX Unsigned32 (6001..6100)
            MAX-ACCESS read-only
            STATUS current
            DESCRIPTION
                "DC unit device ID, which value range: 006,001 to 006,100. The first digits indicate the device type and the last three digits indicate the device SN. "
            ::= { hwDcOutputEntry 2 }

        hwDcOutputEquipName OBJECT-TYPE
            SYNTAX OCTET STRING (SIZE (0..63))
            MAX-ACCESS read-only
            STATUS current
            DESCRIPTION
                "DC unit device name, of the character string type."
            ::= { hwDcOutputEntry 3 }

        hwDcOutputVoltage OBJECT-TYPE
            SYNTAX Unsigned32 (0..1000)
            MAX-ACCESS read-only
            STATUS current
            DESCRIPTION
                "DC output voltage. It is an analog parameter collected by the DC power in real time. 
                Value range: 0 to 100, 
                unit: V, 
                and the value is accurate to one decimal space (.1).  
                If the value is 2147483647(0x7FFFFFFF), it indicates that the value is invalid."
            ::= { hwDcOutputEntry 4 }

        hwDcOutputCurrent OBJECT-TYPE
            SYNTAX Integer32 (0..300000)
            MAX-ACCESS read-only
            STATUS current
            DESCRIPTION
                "DC output current. It is an analog parameter collected by the DC power in real time. 
                Value range: 0.0 to 30000.0, 
                unit: A, 
                and the value is accurate to one decimal space (.1). 
                If the value is 2147483647(0x7FFFFFFF), it indicates that the value is invalid."
            ::= { hwDcOutputEntry 5 }

        hwDcOutputPower OBJECT-TYPE
            SYNTAX Unsigned32 (0..1000000)
            MAX-ACCESS read-only
            STATUS current
            DESCRIPTION
                "DC output power. It is an analog parameter collected by the DC power in real time. 
                Value range: 0 to 10000.00, 
                unit: kW, 
                and the value is an integer (1).  
                If the value is 2147483647(0x7FFFFFFF), it indicates that the value is invalid."
            ::= { hwDcOutputEntry 6 }

        hwLoadsQuantity OBJECT-TYPE
            SYNTAX Unsigned32 (0..30)
            MAX-ACCESS read-only
            STATUS current
            DESCRIPTION
                "Quantity of the DC load output branches, 
                which value range: 0 to 30.  
                As the DC unit lower-level subset, the node indicates the quantity of the DC load output branches contained by each DC unit lower-level subset."
            ::= { hwDcOutputEntry 7 }

        hwLoadUsage OBJECT-TYPE
            SYNTAX Unsigned32 (0..100)
            MAX-ACCESS read-only
            STATUS current
            DESCRIPTION
                "The load usage of rated rectifier capacity. 
                Value range: 0 to 100, 
                unit: %, 
                and the value is an integer (1)."
            ::= { hwDcOutputEntry 8 }

        hwSetDcUpperVoltLimit OBJECT-TYPE
            SYNTAX Unsigned32 (530..600)
            MAX-ACCESS read-write
            STATUS current
            DESCRIPTION
                "Upper threshold of the DC voltage alarm, can be configued by users. 
                Value range: 53 to 60, 
                unit: V, 
                and the value is accurate to one decimal space (.1).  
                If the value is 2147483647(0x7FFFFFFF), it indicates that the value is invalid.
                NOTE: There is linkage between hwSetDcsUpperVoltLimit and hwSetDcsLowerVoltLimit"
            ::= { hwDcOutputEntry 10 }

        hwSetDcLowerVoltLimit OBJECT-TYPE
            SYNTAX Unsigned32 (350..570)
            MAX-ACCESS read-write
            STATUS current
            DESCRIPTION
                "Lower threshold of the DC voltage alarm, can be configued by users. 
                Value range: 35 to 57, 
                unit: V, 
                and the value is accurate to one decimal space (.1).  
                If the value is 2147483647(0x7FFFFFFF), it indicates that the value is invalid.
                NOTE: There is linkage between hwSetDcsUpperVoltLimit and hwSetDcsLowerVoltLimit"
            ::= { hwDcOutputEntry 11 }

        hwDcFatherEquipname OBJECT-TYPE
            SYNTAX OCTET STRING
            MAX-ACCESS read-only
            STATUS current
            DESCRIPTION
                "Name of the parent device of the DC"
            ::= { hwDcOutputEntry 9 }

        hwTotalDcLoadEnergyConsumption OBJECT-TYPE
            SYNTAX Unsigned32 (0..4294967295)
            MAX-ACCESS read-only
            STATUS current
            DESCRIPTION
                "Total DC load energy consumption,Value range: 0 to 4294967295, resolution:10Wh."
            ::= { hwDcOutputEntry 12 }

        hwDcDistriIcbdNum OBJECT-TYPE
            SYNTAX Unsigned32 (0..65535)
            MAX-ACCESS read-only
            STATUS current
            DESCRIPTION
                "DC output distribution total icbds."
            ::= { hwDcOutputEntry 13 }

        hwDcDistriCommNormalIcbdNum OBJECT-TYPE
            SYNTAX Unsigned32 (0..65535)
            MAX-ACCESS read-only
            STATUS current
            DESCRIPTION
                "DC output distribution total iCBDs communicating normally."
            ::= { hwDcOutputEntry 14 }

        hwDcDistriLoadFuseStatus1 OBJECT-TYPE
            SYNTAX Unsigned32 (0..4294967295)
            MAX-ACCESS read-only
            STATUS current
            DESCRIPTION
                "DC output distribution Load Fuse Status.
                Expressed in bit positions, 0 indicates normal, 1 indicates open  
                Bit 0 is Load Fuse 1  
                ...  
                Bit 31 is Load Fuse 32"
            ::= { hwDcOutputEntry 15 }

        hwDcDistriLoadFuseStatus2 OBJECT-TYPE
            SYNTAX Unsigned32 (0..4294967295)
            MAX-ACCESS read-only
            STATUS current
            DESCRIPTION
                "DC output distribution Load Fuse Status.
                Expressed in bit positions, 0 indicates normal, 1 indicates open  
                Bit 0 is Load Fuse 33  
                ...  
                Bit 9 is Load Fuse 42
                Bit 10~31 Reversed"
            ::= { hwDcOutputEntry 16 }

        hwDcOutputOperStatus OBJECT-TYPE
            SYNTAX INTEGER
                {
                normal(1),
                voltHigh(2),
                voltLow(3),
                dcAbsent(4),
                overload(5),
                alarmResume(254),
                unknown(255)
                }
            MAX-ACCESS read-only
            STATUS current
            DESCRIPTION
                "State of the site DC distribution uint. It is an enumeration type: 
                If the enumeration value is 1, it indicates that the site DC distribution uint is in the normal state; 
                If the enumeration value is 2, it indicates that DC voltage is over the upper alarm threshold;
                If the enumeration value is 3, it indicates that DC voltage is under the lower alarm threshold; 
                If the enumeration value is 4, it indicates that DC voltage is dcAbsent; 
                If the enumeration value is 5, it indicates that DC voltage is overload; 
                If the enumeration value is 254, it indicates DC distribution uint alarm resume; 
                If the enumeration value is 255, it indicates DC distribution uint operation status unknown. "
            ::= { hwDcOutputEntry 99 }

        hwDcOutputRowStatus OBJECT-TYPE
            SYNTAX RowStatus
            MAX-ACCESS read-create
            STATUS current
            DESCRIPTION
                "RowStatus of Dc output equipments."
            ::= { hwDcOutputEntry 100 }

        hwLoadBranchTable OBJECT-TYPE
            SYNTAX SEQUENCE OF HwLoadBranchEntry
            MAX-ACCESS not-accessible
             STATUS current
             DESCRIPTION
                "Loads output table. Use this table to get load branch equipment ID, load branch equipment name, load branch current, and load branch power. This table's index is hwLoadBranchIndex, which qualificated by hwloadsQuantity in hwDcOutputTable, clone loads output table."
            ::= { hwDcDistribution 2 }

        hwLoadBranchEntry OBJECT-TYPE
                        SYNTAX HwLoadBranchEntry
            MAX-ACCESS not-accessible
             STATUS current
             DESCRIPTION
                "Loads output table. Use this table to get load branch equipment ID, load branch equipment name, load branch current, and load branch power. This table's index is hwLoadBranchIndex, which qualificated by hwloadsQuantity in hwDcOutputTable, clone loads output table."
            INDEX { hwLoadBranchIndex }
            ::= { hwLoadBranchTable 1 }

        HwLoadBranchEntry            ::= SEQUENCE {
                hwLoadBranchIndex
                    Integer32,
                hwLoadBranchEquipId
                    Unsigned32,
                hwLoadBranchEquipName
                    OCTET STRING,
                hwLoadBranchCurrent
                    Integer32,
                hwLoadBranchPower
                    Unsigned32,
                hwLoadBranchOperStatus
                    INTEGER,
                hwLoadBranchConsume
                    Unsigned32,
                hwLoadBranchConsumption
                    Unsigned32,
                hwLoadBranchConsumptionLow32b
                    Unsigned32,
                hwLoadBranchConsumptionHigh32b
                    Unsigned32,
                hwLoadBranchFatherEquipname
                    OCTET STRING,
                hwLoadBranchEnergyConsumption
                    Unsigned32
            }

        hwLoadBranchIndex OBJECT-TYPE
            SYNTAX Integer32 (1..100)
            MAX-ACCESS read-only
            STATUS current
            DESCRIPTION
                "Device table index of the DC load output branch, 
                which value range: 1 to 100.  
                A DC load output branch can be uniquely identified through the DC unit table index and device index of the DC load output branch."
            ::= { hwLoadBranchEntry 1 }

        hwLoadBranchEquipId OBJECT-TYPE
            SYNTAX Unsigned32
            MAX-ACCESS read-only
            STATUS current
            DESCRIPTION
                "Device ID of the DC load output branch. Value range: 007,001 to 007,100. The first digits indicate the device type and the last three digits indicate the SN of the device. "
            ::= { hwLoadBranchEntry 2 }

        hwLoadBranchEquipName OBJECT-TYPE
            SYNTAX OCTET STRING (SIZE (0..63))
            MAX-ACCESS read-only
            STATUS current
            DESCRIPTION
                "Device name of the DC load output branch, of the character string type."
            ::= { hwLoadBranchEntry 3 }

        hwLoadBranchCurrent OBJECT-TYPE
            SYNTAX Integer32 (-300000..300000)
            MAX-ACCESS read-only
            STATUS current
            DESCRIPTION
                "DC load output branch current. It is an analog parameter collected by the load branch in real time. 
                Value range: -30000.0 to 30000.0, 
                units: A, 
                and the value is accurate to one decimal space (.1).  
                If the value is 2147483647(0x7FFFFFFF), it indicates that the value is invalid."
            ::= { hwLoadBranchEntry 4 }

        hwLoadBranchPower OBJECT-TYPE
            SYNTAX Unsigned32 (0..600000)
            MAX-ACCESS read-only
            STATUS current
            DESCRIPTION
                "DC load branch power. It is an analog parameter collected by the DC power in real time. 
                Value range: 0 to 3000000, 
                unit: W, 
                and the value is an integer (1).  
                If the value is 2147483647(0x7FFFFFFF), it indicates that the value is invalid."
            ::= { hwLoadBranchEntry 5 }

        hwLoadBranchOperStatus OBJECT-TYPE
            SYNTAX INTEGER
                {
                normal(1),
                disconnect(2),
                noresponse(3),
                overload(4),
                alarmResume(254),
                unknown(255)
                }
            MAX-ACCESS read-only
            STATUS current
            DESCRIPTION
                "State of the site load output branch. It is an enumeration type: 
                If the enumeration value is 1, it indicates that the site load output branch is in the normal state; 
                If the enumeration value is 2, it indicates that the load output branch disconnect;
                If the enumeration value is 3, it indicates that the site load output branch is in noresponse state; 
                If the enumeration value is 4, it indicates that the site load output branch is in the overload state; 
                If the enumeration value is 254, it indicates load output branch alarm resume; 
                If the enumeration value is 255, it indicates load output branch operation status unknown. "
            ::= { hwLoadBranchEntry 7 }

        hwLoadBranchConsume OBJECT-TYPE
            SYNTAX Unsigned32 (0..4294967295)
            MAX-ACCESS read-only
            STATUS current
            DESCRIPTION
                "DC load branch power consumption,
                Value range: 0 to 4294967295, 
                unit: KWh, 
                and the value is accurate to one decimal space (.1)."
            ::= { hwLoadBranchEntry 6 }

        hwLoadBranchConsumption OBJECT-TYPE
            SYNTAX Unsigned32 (0..4294967295)
            MAX-ACCESS read-only
            STATUS current
            DESCRIPTION
                "DC load branch power consumption,Value range: 0 to 4294967295, resolution:1 KWh."
            ::= { hwLoadBranchEntry 8 }

        hwLoadBranchConsumptionLow32b OBJECT-TYPE
            SYNTAX Unsigned32 (0..4294967295)
            MAX-ACCESS read-only
            STATUS current
            DESCRIPTION
                "Low 32 bits of DC load branch power consumption,Value range: 0 to 4294967295, resolution:10Wh"
            ::= { hwLoadBranchEntry 9 }

        hwLoadBranchConsumptionHigh32b OBJECT-TYPE
            SYNTAX Unsigned32 (0..4294967295)
            MAX-ACCESS read-only
            STATUS current
            DESCRIPTION
                "High 32 bits of DC load branch power consumption,Value range: 0 to 4294967295, resolution:10Wh"
            ::= { hwLoadBranchEntry 10 }

        hwLoadBranchFatherEquipname OBJECT-TYPE
            SYNTAX OCTET STRING
            MAX-ACCESS read-only
            STATUS current
            DESCRIPTION
                "Name of the parent device of the load output branch."
            ::= { hwLoadBranchEntry 11 }

        hwLoadBranchEnergyConsumption OBJECT-TYPE
            SYNTAX Unsigned32 (0..4294967295)
            MAX-ACCESS read-only
            STATUS current
            DESCRIPTION
                "DC load branch energy consumption,Value range: 0 to 4294967295, resolution:10Wh"
            ::= { hwLoadBranchEntry 12 }

        hwLvdUnits OBJECT IDENTIFIER ::= { hwSiteMonitorMIBObjects 7 }

        hwLvdsGroup OBJECT IDENTIFIER ::= { hwLvdUnits 1 }

        hwLvdsGroupId OBJECT-TYPE
            SYNTAX Unsigned32
            MAX-ACCESS read-only
            STATUS current
            DESCRIPTION
                "LVD unit group ID. It is the unique ID of the LVD unit group. The first digits indicate the device type. The last three digits indicate the device SN. If the last three digits are 000, it indicates a virtual device."
            ::= { hwLvdsGroup 1 }

        hwLvdsGroupName OBJECT-TYPE
            SYNTAX OCTET STRING (SIZE (0..63))
            MAX-ACCESS read-write
            STATUS current
            DESCRIPTION
                "Low-voltage power-off unit group name, of the character string type, can be configured by users.
                Otherwise, the configured character can not be any other languages except English."
            ::= { hwLvdsGroup 2 }

        hwLvdsTotalQuantity OBJECT-TYPE
            SYNTAX Unsigned32 (0..100)
            MAX-ACCESS read-only
            STATUS current
            DESCRIPTION
                "Device table index of a power-off unit. 
                
                Value range: 1 to 100. Lines of the device list are restricted by the total quantity of the power-off units (hwLvdsTotalQuantity). "
            ::= { hwLvdsGroup 3 }

        hwLvdUnit OBJECT IDENTIFIER ::= { hwLvdUnits 2 }

        hwLvdBranchTable OBJECT-TYPE
            SYNTAX SEQUENCE OF HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            ::= { hwLvdUnit 1 }

        hwLvdBranchEntry OBJECT-TYPE
                        SYNTAX HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            INDEX { hwLvdBranchIndex }
            ::= { hwLvdBranchTable 1 }

        HwLvdBranchEntry            ::= SEQUENCE {
                hwLvdBranchIndex
                    Integer32,
                hwLvdUnitEquipId
                    Unsigned32,
                hwLvdUnitEquipName
                    OCTET STRING,
                hwSetLvdEnable
                    INTEGER,
                hwSetLvdVoltage
                    Integer32,
                hwCtrlLvd
                    INTEGER,
                hwSetLvdMode
                    INTEGER,
                hwSetLvdReconnectedVoltage
                    Integer32,
                hwSetLvdDisconnectedTime
                    Integer32,
                hwSetLvdDisconnectedCapacity
                    Integer32,
                hwLvdBranchOperStatus
                    INTEGER,
                hwLvdBranchRowStatus
                    RowStatus
            }

        hwLvdBranchIndex OBJECT-TYPE
            SYNTAX Integer32 (1..100)
            MAX-ACCESS read-only
            STATUS current
            DESCRIPTION
                "Device table index of a power-off unit. 
                Value range: 1 to 100. Lines of the device list are restricted by the total quantity of the power-off units (hwLvdsTotalQuantity). "
            ::= { hwLvdBranchEntry 1 }

        hwLvdUnitEquipId OBJECT-TYPE
            SYNTAX Unsigned32 (8001..8100)
            MAX-ACCESS read-only
            STATUS current
            DESCRIPTION
                "Device ID of a power-off unit."
            ::= { hwLvdBranchEntry 2 }

        hwLvdUnitEquipName OBJECT-TYPE
            SYNTAX OCTET STRING (SIZE (0..63))
            MAX-ACCESS read-only
            STATUS current
            DESCRIPTION
                "Device name of a power-off unit, of the character string type, is used to specify the low-voltage power-off unit. Users can configure it. Otherwise, the configured character can not be any other languages except English. "
            ::= { hwLvdBranchEntry 3 }

        hwSetLvdEnable OBJECT-TYPE
            SYNTAX INTEGER
                {
                enabled(1),
                disabled(2)
                }
            MAX-ACCESS read-write
            STATUS current
            DESCRIPTION
                "Control power-off unit enabling. It is an enumeration value, and users actively set it. 
                  If the enumeration value is 1, it means to enable the power-off unit; 
                  If the enumeration value is 2, it means to disable the power-off unit. 
                  When the power-off unit control is not configured, the power-off unit is enabled by default."
            ::= { hwLvdBranchEntry 4 }

        hwSetLvdVoltage OBJECT-TYPE
            SYNTAX Integer32 (360..560)
            MAX-ACCESS read-write
            STATUS current
            DESCRIPTION
                "Low-voltage power-off voltage of a power-off unit can be configured by users. 
                Its value range: 36 to 56, 
                unit: V, 
                and the value is accurate to one decimal space (.1).  
                If the value is 2147483647(0x7FFFFFFF), it indicates that the value is invalid.
                NOTE: There is linkage between hwSetLvdVoltage and hwSetLvdReconnectedVoltage"
            ::= { hwLvdBranchEntry 5 }

        hwCtrlLvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the LVD unit. 
                  If the NMS notifies the SNMP agent that the node is set to 255, it means that the background controls the nulloper of the LVD unit.
                NOTE: Only the system in manual mode, this parameter can be configured successfully.
                "
            ::= { hwLvdBranchEntry 6 }

        hwSetLvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwLvdBranchEntry 7 }

        hwSetLvdReconnectedVoltage OBJECT-TYPE
            SYNTAX Integer32 (370..580)
            MAX-ACCESS read-write
            STATUS current
            DESCRIPTION
                ""
            ::= { hwLvdBranchEntry 8 }

        hwSetLvdDisconnectedTime OBJECT-TYPE
            SYNTAX Integer32 (0..1000)
            MAX-ACCESS read-write
            STATUS current
            DESCRIPTION
                "Low-voltage power-off disconnected time, It can be configured by users,
                value range defines between 0 to 1000, 
                unit: minutes(min) ，
                and its value is an integer (1). 
                Here, if battery manual test is standard mode, 
                If the value is 2147483647(0x7FFFFFFF), it indicates that the value is invalid.
                NOTE: Only the lvd in time power off mode, this parameter can be configured successfully."
            ::= { hwLvdBranchEntry 9 }

        hwSetLvdDisconnectedCapacity OBJECT-TYPE
            SYNTAX Integer32 (0..990)
            MAX-ACCESS read-write
            STATUS current
            DESCRIPTION
                "Power-off unit control the power off, when Remaining capacity percentage of the battery strings is below the calue. 
                Value range: 0 to 99.0, 
                unit: %, 
                and the value is accurate to one decimal space (.1).  
                If the value is 2147483647(0x7FFFFFFF), it indicates that the value is invalid.
                NOTE: Only the lvd in capacity power off mode, this parameter can be configured successfully."
            ::= { hwLvdBranchEntry 10 }

        hwLvdBranchOperStatus OBJECT-TYPE
            SYNTAX INTEGER
                {
                normal(1),
                lowVoltOff(2),
                backgroundOff(3),
                localManualOff(4),
                lowTempOff(5),
                highTempOff(6),
                timeOff(7),
                capacityOff(8),
                forceOff(9),
                maintenanceOff(10),
                alarmResume(254),
                unknown(255)
                }
            MAX-ACCESS read-only
            STATUS current
            DESCRIPTION
                "State of the site LVD uint. It is an enumeration type: 
                  If the enumeration value is 1, the site LVD uint is in the normal state;
                  If the enumeration value is 2, the power-off uint disconnect for low voltage;  
                  If the enumeration value is 3, the power-off uint disconnect bakeground;   
                  If the enumeration value is 4, the power-off uint local disconnect manually;  
                  If the enumeration value is 5, the power-off uint disconnect for under temperature; 
                  If the enumeration value is 6, the power-off uint disconnect for over temperature; 
                  If the enumeration value is 7, the ower-off uint disconnect for time;
                If the enumeration value is 8, the power-off uint disconnect for capacity;
                If the enumeration value is 9, the power-off uint disconnect for force;
                If the enumeration value is 10, the power-off uint disconnect for maintenance;
                  If the enumeration value is 254, the power-off uint alarm resume; 
                  If the enumeration value is 255, it indicates LVD uint operation status unknown. "
            ::= { hwLvdBranchEntry 99 }

        hwLvdBranchRowStatus OBJECT-TYPE
            SYNTAX RowStatus
            MAX-ACCESS read-create
            STATUS current
            DESCRIPTION
                "RowStatus of lvd table."
            ::= { hwLvdBranchEntry 100 }

        hwDcLvdTable OBJECT-TYPE
            SYNTAX SEQUENCE OF HwDcLvdEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            ::= { hwLvdUnit 2 }

        hwDcLvdEntry OBJECT-TYPE
                        SYNTAX HwDcLvdEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            INDEX { hwDcLvdIndex }
            ::= { hwDcLvdTable 1 }

        HwDcLvdEntry            ::= SEQUENCE {
                hwDcLvdIndex
                    Integer32,
                hwDcLvdEquipId
                    Unsigned32,
                hwDcLvdEquipName
                    OCTET STRING,
                hwDcSetLvdEnable
                    INTEGER,
                hwDcSetLvdVoltage
                    Integer32,
                hwDcCtrlLvd
                    INTEGER,
                hwDcSetLvdMode
                    INTEGER,
                hwDcSetLvdReconnectedVoltage
                    Integer32,
                hwDcSetLvdDisconnectedTime
                    Integer32,
                hwDcSetLvdDisconnectedCapacity
                    Integer32,
                hwDcLvdFatherEquipname
                    OCTET STRING
            }

        hwDcLvdIndex OBJECT-TYPE
            SYNTAX Integer32 (1..100)
            MAX-ACCESS read-only
            STATUS current
            DESCRIPTION
                "Device table index of a power-off unit. 
                Value range: 1 to 100. Lines of the device list are restricted by the total quantity of the power-off units (hwLvdsTotalQuantity). "
            ::= { hwDcLvdEntry 1 }

        hwDcLvdEquipId OBJECT-TYPE
            SYNTAX Unsigned32
            MAX-ACCESS read-only
            STATUS current
            DESCRIPTION
                "Device ID of a power-off unit."
            ::= { hwDcLvdEntry 2 }

        hwDcLvdEquipName OBJECT-TYPE
            SYNTAX OCTET STRING (SIZE (0..63))
            MAX-ACCESS read-only
            STATUS current
            DESCRIPTION
                "Device name of a power-off unit, of the character string type, is used to specify the low-voltage power-off unit. Users can configure it. Otherwise, the configured character can not be any other languages except English. "
            ::= { hwDcLvdEntry 3 }

        hwDcSetLvdEnable OBJECT-TYPE
            SYNTAX INTEGER
                {
                enabled(1),
                disabled(2)
                }
            MAX-ACCESS read-write
            STATUS current
            DESCRIPTION
                "Control power-off unit enabling. It is an enumeration value, and users actively set it. 
                If the enumeration value is 1, it means to enable the power-off unit; 
                If the enumeration value is 2, it means to disable the power-off unit. 
                When the power-off unit control is not configured, the power-off unit is enabled by default.
                Instance number:
                1---LLVD1
                2---LLVD2
                3---BLVD
                4---LLVD3
                5---LLVD4"
            ::= { hwDcLvdEntry 4 }

        hwDcSetLvdVoltage OBJECT-TYPE
            SYNTAX Integer32 (350..560)
            MAX-ACCESS read-write
            STATUS current
            DESCRIPTION
                "Low-voltage power-off voltage of a power-off unit can be configured by users. 
                Its value range: 35 to 56, 
                unit: V, 
                and the value is accurate to one decimal space (.1).  
                If the value is 2147483647(0x7FFFFFFF), it indicates that the value is invalid.
                NOTE: There is linkage between hwSetLvdVoltage and hwSetLvdReconnectedVoltage"
            ::= { hwDcLvdEntry 5 }

        hwDcCtrlLvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the LVD unit. 
                  If the NMS notifies the SNMP agent that the node is set to 255, it means that the background controls the nulloper of the LVD unit.
                NOTE: Only the system in manual mode, this parameter can be configured successfully.
                "
            ::= { hwDcLvdEntry 6 }

        hwDcSetLvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwDcLvdEntry 7 }

        hwDcSetLvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                The default value is 51.5
                NOTE: There is linkage between hwSetLvdVoltage and hwSetLvdReconnectedVoltage"
            ::= { hwDcLvdEntry 8 }

        hwDcSetLvdDisconnectedTime OBJECT-TYPE
            SYNTAX Integer32 (0..1000)
            MAX-ACCESS read-write
            STATUS current
            DESCRIPTION
                "Low-voltage power-off disconnected time, It can be configured by users,
                value range defines between 0 to 1000, 
                unit: minutes(min) ，
                and its value is an integer (1). 
                Here, if battery manual test is standard mode, 
                If the value is 2147483647(0x7FFFFFFF), it indicates that the value is invalid.
"
            ::= { hwDcLvdEntry 9 }

        hwDcSetLvdDisconnectedCapacity OBJECT-TYPE
            SYNTAX Integer32 (0..990)
            MAX-ACCESS read-write
            STATUS current
            DESCRIPTION
                "Power-off unit control the power off, when Remaining capacity percentage of the battery strings is below the calue. 
                Value range: 0 to 99.0, 
                unit: %, 
                and the value is accurate to one decimal space (.1).  
                If the value is 2147483647(0x7FFFFFFF), it indicates that the value is invalid.
                "
            ::= { hwDcLvdEntry 10 }

        hwDcLvdFatherEquipname OBJECT-TYPE
            SYNTAX OCTET STRING
            MAX-ACCESS read-only
            STATUS current
            DESCRIPTION
                "Name of the parent device of the power-off unit"
            ::= { hwDcLvdEntry 11 }

        hwBlvdTable OBJECT-TYPE
            SYNTAX SEQUENCE OF HwBlvdEntry
            MAX-ACCESS not-accessible
             STATUS current
             DESCRIPTION
                "Power-off unit table."
            ::= { hwLvdUnit 3 }

        hwBlvdEntry OBJECT-TYPE
                        SYNTAX HwBlvdEntry
            MAX-ACCESS not-accessible
             STATUS current
             DESCRIPTION
                "Power-off unit table."
            INDEX { hwBlvdIndex }
            ::= { hwBlvdTable 1 }

        HwBlvdEntry            ::= SEQUENCE {
                hwBlvdIndex
                    Integer32,
                hwBlvdEquipId
                    Unsigned32,
                hwBlvdEquipName
                    OCTET STRING,
                hwSetBlvdEnable
                    INTEGER,
                hwSetBlvdVoltage
                    Integer32,
                hwCtrlBlvd
                    INTEGER,
                hwSetBlvdMode
                    INTEGER,
                hwSetBlvdReconnectedVoltage
                    Integer32,
                hwSetBlvdDisconnectedTime
                    Integer32,
                hwSetBlvdDisconnectedCapacity
                    Integer32,
                hwBlvdFatherEquipname
                    OCTET STRING
            }

        hwBlvdIndex OBJECT-TYPE
            SYNTAX Integer32 (1..100)
            MAX-ACCESS read-only
            STATUS current
            DESCRIPTION
                "Device table index of a power-off unit. "
            ::= { hwBlvdEntry 1 }

        hwBlvdEquipId OBJECT-TYPE
            SYNTAX Unsigned32
            MAX-ACCESS read-only
            STATUS current
            DESCRIPTION
                "Device ID of a power-off unit."
            ::= { hwBlvdEntry 2 }

        hwBlvdEquipName OBJECT-TYPE
            SYNTAX OCTET STRING (SIZE (0..63))
            MAX-ACCESS read-only
            STATUS current
            DESCRIPTION
                "Device name of a power-off unit"
            ::= { hwBlvdEntry 3 }

        hwSetBlvdEnable OBJECT-TYPE
            SYNTAX INTEGER
                {
                enabled(1),
                disabled(2)
                }
            MAX-ACCESS read-write
            STATUS current
            DESCRIPTION
                "Control power-off unit enabling. It is an enumeration value, and users actively set it. 
                  If the enumeration value is 1, it means to enable the power-off unit; 
                  If the enumeration value is 2, it means to disable the power-off unit. 
                  When the power-off unit control is not configured, the power-off unit is enabled by default."
            ::= { hwBlvdEntry 4 }

        hwSetBlvdVoltage OBJECT-TYPE
            SYNTAX Integer32 (360..560)
            MAX-ACCESS read-write
            STATUS current
            DESCRIPTION
                "Low-voltage power-off voltage of a power-off unit can be configured by users. 
                Its value range: 36 to 56, 
                unit: V, 
                and the value is accurate to one decimal space (.1).  
                If the value is 2147483647(0x7FFFFFFF), it indicates that the value is invalid.
                NOTE: There is linkage between hwSetBlvdVoltage and hwSetBlvdReconnectedVoltage"
            ::= { hwBlvdEntry 5 }

        hwCtrlBlvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the Blvd unit. 
                  If the NMS notifies the SNMP agent that the node is set to 255, it means that the background controls the nulloper of the Blvd unit.
                NOTE: Only the system in manual mode, this parameter can be configured successfully.
                "
            ::= { hwBlvdEntry 6 }

        hwSetBlvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwBlvdEntry 7 }

        hwSetBlvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                NOTE: There is linkage between hwSetBlvdVoltage and hwSetBlvdReconnectedVoltage"
            ::= { hwBlvdEntry 8 }

        hwSetBlvdDisconnectedTime OBJECT-TYPE
            SYNTAX Integer32 (5..1000)
            MAX-ACCESS read-write
            STATUS current
            DESCRIPTION
                "Low-voltage power-off disconnected time, It can be configured by users,
                value range defines between 5 to 1000, 
                unit: minutes(min) ，
                and its value is an integer (1). 
                Here, if battery manual test is standard mode, 
                If the value is 2147483647(0x7FFFFFFF), it indicates that the value is invalid.
                NOTE: Only the Blvd in time power off mode, this parameter can be configured successfully."
            ::= { hwBlvdEntry 9 }

        hwSetBlvdDisconnectedCapacity OBJECT-TYPE
            SYNTAX Integer32 (0..990)
            MAX-ACCESS read-write
            STATUS current
            DESCRIPTION
                "Power-off unit control the power off, when Remaining capacity percentage of the battery strings is below the calue. 
                Value range: 0 to 99.0, 
                unit: %, 
                and the value is accurate to one decimal space (.1).  
                If the value is 2147483647(0x7FFFFFFF), it indicates that the value is invalid.
                NOTE: Only the Blvd in capacity power off mode, this parameter can be configured successfully."
            ::= { hwBlvdEntry 10 }

        hwBlvdFatherEquipname OBJECT-TYPE
            SYNTAX OCTET STRING
            MAX-ACCESS read-only
            STATUS current
            DESCRIPTION
                "Name of the parent device of the power-off unit"
            ::= { hwBlvdEntry 11 }

        hwSiteEnvUnits OBJECT IDENTIFIER ::= { hwSiteMonitorMIBObjects 8 }

        hwEnvUnitsGroup OBJECT IDENTIFIER ::= { hwSiteEnvUnits 1 }

        hwEnvUnitsGroupId OBJECT-TYPE
            SYNTAX Unsigned32
            MAX-ACCESS read-only
            STATUS current
            DESCRIPTION
                "Unit group ID of the site environment. It is the unique ID of the unit group on the site. 
                The first digits indicate the device type. The last three digits indicate the device SN. If the last three digits are 000, it indicates a virtual device. "
            ::= { hwEnvUnitsGroup 1 }

        hwEnvUnitsGroupName OBJECT-TYPE
            SYNTAX OCTET STRING (SIZE (0..63))
            MAX-ACCESS read-write
            STATUS current
            DESCRIPTION
                "Unit group name of the site environment, of the character string type, can be configured by users.
                Otherwise, the configured character can not be any other languages except English."
            ::= { hwEnvUnitsGroup 2 }

        hwCtrlSmokeReset OBJECT-TYPE
            SYNTAX INTEGER
                {
                reset(2),
                nullOper(255)
                }
            MAX-ACCESS read-write
            STATUS current
            DESCRIPTION
                "Smoke sensor reset. It manually controls clearance of the smoke sensor alarm, and this node is of the enumeration type. 
                If the enumeration value of the node is 2, it indicates that the background controls the reset of the smoke sensor. 
                If the enumeration value of the node is 255, it indicates that the background controls the unknown of the smoke sensor. "
            ::= { hwEnvUnitsGroup 3 }

        hwCtrlBuzzerEnable OBJECT-TYPE
            SYNTAX INTEGER
                {
                enable(1),
                disable(2),
                nullOper(255)
                }
            MAX-ACCESS read-write
            STATUS current
            DESCRIPTION
                "Buzzer enabling. It manually controls the enabling of the buzzer alarm. This node is of the enumeration type. 
                When the enumeration value is 1, it means to enable the buzzer;
                When the enumeration value is 2, it means to disable the buzzer. 
                When the enumeration value is 255, it means to nulloper the buzzer. 
                Note: This MIB node has been specially processed using the RegisterDifferSignalHandleType() method, and the node values and signal values have a non enumeration mapping relationship.
                "
            ::= { hwEnvUnitsGroup 5 }

        hwEnvTempSensorsTotalQuantity OBJECT-TYPE
            SYNTAX Unsigned32 (0..256)
            MAX-ACCESS read-only
            STATUS current
            DESCRIPTION
                "Quantity of the environment temperature sensors, and its value range: 0 to 256."
            ::= { hwEnvUnitsGroup 6 }

        hwEnvHumiSensorsTotalQuantity OBJECT-TYPE
            SYNTAX Unsigned32 (0..256)
            MAX-ACCESS read-only
            STATUS current
            DESCRIPTION
                "Quantity of the environment humidity sensors, and its value range: 0 to 256."
            ::= { hwEnvUnitsGroup 7 }

        hwSpareDigitalsTotalQuantity OBJECT-TYPE
            SYNTAX Unsigned32 (0..256)
            MAX-ACCESS read-only
            STATUS current
            DESCRIPTION
                "Quantity of the Spare digitals, and its value range: 0 to 256."
            ::= { hwEnvUnitsGroup 8 }

        hwSpareDigitalsOutputQuantity OBJECT-TYPE
            SYNTAX Unsigned32 (0..256)
            MAX-ACCESS read-only
            STATUS current
            DESCRIPTION
                "Quantity of the Spare digitals Output, and its value range: 0 to 256."
            ::= { hwEnvUnitsGroup 9 }

        hwEnvSensor OBJECT IDENTIFIER ::= { hwSiteEnvUnits 2 }

        hwEnvTempSensorTable OBJECT-TYPE
            SYNTAX SEQUENCE OF HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            ::= { hwEnvSensor 1 }

        hwEnvTempSensorEntry OBJECT-TYPE
                        SYNTAX HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            INDEX { hwEnvTempSensorIndex }
            ::= { hwEnvTempSensorTable 1 }

        HwEnvTempSensorEntry            ::= SEQUENCE {
                hwEnvTempSensorIndex
                    Integer32,
                hwEnvTempEquipId
                    Unsigned32,
                hwEnvTempEquipName
                    OCTET STRING,
                hwEnvTemperature
                    Integer32,
                hwSetEnvTempUpperLimit
                    Integer32,
                hwSetEnvTempLowerLimit
                    Integer32,
                hwSetEnvTempUltraHighTempThreshold
                    Unsigned32,
                hwEnvTempSensorOperStatus
                    INTEGER,
                hwEnvTempFatherEquipname
                    OCTET STRING,
                hwEnvTempSensorRowStatus
                    RowStatus
            }

        hwEnvTempSensorIndex OBJECT-TYPE
            SYNTAX Integer32
            MAX-ACCESS read-only
            STATUS current
            DESCRIPTION
                "Table index of the environment temperature sensors."
            ::= { hwEnvTempSensorEntry 1 }

        hwEnvTempEquipId OBJECT-TYPE
            SYNTAX Unsigned32 (9001..9255)
            MAX-ACCESS read-only
            STATUS current
            DESCRIPTION
                "Environment temperature sensor ID. Value range: 009'001 to 009'255, in which the first digits indicate the device type and the last three digits indicate the device SN. "
            ::= { hwEnvTempSensorEntry 2 }

        hwEnvTempEquipName OBJECT-TYPE
            SYNTAX OCTET STRING (SIZE (0..63))
            MAX-ACCESS read-only
            STATUS current
            DESCRIPTION
                "Environment temperature sensor name, of the character string type,  is used to specify an environment temperature sensor. "
            ::= { hwEnvTempSensorEntry 3 }

        hwEnvTemperature OBJECT-TYPE
            SYNTAX Integer32 ( -20..80)
            MAX-ACCESS read-only
            STATUS current
            DESCRIPTION
                "Environment temperature. It is an environment parameter collected in real time. 
                Value range: -20 to +80, 
                unit: centigrade (degC), 
                and the value is an integer (1).  
                If the value is 2147483647, it indicates that the temperature sensor is not configured."
            ::= { hwEnvTempSensorEntry 4 }

        hwSetEnvTempUpperLimit OBJECT-TYPE
            SYNTAX Integer32
            MAX-ACCESS read-write
            STATUS current
            DESCRIPTION
                "Upper threshold of the environment temperature alarm, can be configured by users. 
                unit: centigrade (degC), 
                and the value is an integer (1). 
                If the value is 2147483647(0x7FFFFFFF), it indicates that the value is invalid.
                NOTE: There is linkage between hwSetEnvTempUpperLimit and hwSetEnvTempLowerLimit.
                If the result of the setting returns an error, it means that it is not supported."
            ::= { hwEnvTempSensorEntry 5 }

        hwSetEnvTempLowerLimit OBJECT-TYPE
            SYNTAX Integer32
            MAX-ACCESS read-write
            STATUS current
            DESCRIPTION
                "Lower threshold of the environment temperature alarm, can be configured by users. 
                unit: centigrade (degC), 
                and the value is an integer (1).  
                If the value is 2147483647(0x7FFFFFFF), it indicates that the value is invalid.
                NOTE: There is linkage between hwSetEnvTempUpperLimit and hwSetEnvTempLowerLimit.
                If the result of the setting returns an error, it means that it is not supported."
            ::= { hwEnvTempSensorEntry 6 }

        hwSetEnvTempUltraHighTempThreshold OBJECT-TYPE
            SYNTAX Unsigned32 (25..80)
            MAX-ACCESS read-write
            STATUS current
            DESCRIPTION
                "Threshold of the environment ultra high temperature measurement, can be configured by users.
                unit: centigrade (degC),
                and the value is an integer (1).
                If the value is 2147483647(0x7FFFFFFF), it indicates that the value is invalid.
                If the result of the setting returns an error, it means that it is not supported.
                "
            ::= { hwEnvTempSensorEntry 10 }

        hwEnvTempSensorOperStatus OBJECT-TYPE
            SYNTAX INTEGER
                {
                normal(1),
                tempHigh(2),
                tempLow(3),
                notInslot(4),
                alarmResume(254),
                unknown(255)
                }
            MAX-ACCESS read-only
            STATUS current
            DESCRIPTION
                "State of the site environment temperature sensor. It is an enumeration type: 
                  If the enumeration value is 1, it indicates that the site environment temperature sensor is in the normal state; 
                  If the enumeration value is 2, it indicates that the environment temperature sensor is over temperature; 
                  If the enumeration value is 3, it indicates that the environment temperature sensor is under temperature; 
                  If the enumeration value is 4, it indicates that the environment temperature sensor is not in slot;
                  If the enumeration value is 254, it indicates that environment temperature alarm resume; 
                  If the enumeration value is 255, it indicates environment temperature sensor operation status unknown. "
            ::= { hwEnvTempSensorEntry 99 }

        hwEnvTempFatherEquipname OBJECT-TYPE
            SYNTAX OCTET STRING
            MAX-ACCESS read-only
            STATUS current
            DESCRIPTION
                "Name of the parent device of the Environment temperature "
            ::= { hwEnvTempSensorEntry 11 }

        hwEnvTempSensorRowStatus OBJECT-TYPE
            SYNTAX RowStatus
            MAX-ACCESS read-create
            STATUS current
            DESCRIPTION
                "RowStatus of Environment temperature table."
            ::= { hwEnvTempSensorEntry 100 }

        hwEnvHumiSensorTable OBJECT-TYPE
            SYNTAX SEQUENCE OF HwEnvHumiSensorEntry
            MAX-ACCESS not-accessible
             STATUS current
             DESCRIPTION
                "Environment humidity table. Use this table to get environment humidity equipment ID , environment humidity equipment name, and environment humidity, set environment humidity upper limit, environment humidity lower limit, and environment humidity alarm enable. 
                This table's index is hwEnvHumiSensorIndex, which qualificated by hwEnvHumiSensorIndex, clone site environment humidity table."
            ::= { hwEnvSensor 2 }

        hwEnvHumiSensorEntry OBJECT-TYPE
                        SYNTAX HwEnvHumiSensorEntry
            MAX-ACCESS not-accessible
             STATUS current
             DESCRIPTION
                "Environment humidity table. Use this table to get environment humidity equipment ID , environment humidity equipment name, and environment humidity, set environment humidity upper limit, environment humidity lower limit, and environment humidity alarm enable. 
                This table's index is hwEnvHumiSensorIndex, which qualificated by hwEnvHumiSensorIndex, clone site environment humidity table."
            INDEX { hwEnvHumiSensorIndex }
            ::= { hwEnvHumiSensorTable 1 }

        HwEnvHumiSensorEntry            ::= SEQUENCE {
                hwEnvHumiSensorIndex
                    Integer32,
                hwEnvHumiEquipId
                    Unsigned32,
                hwEnvHumiEquipName
                    OCTET STRING,
                hwEnvHumidity
                    Integer32,
                hwSetEnvHumidityUpperLimit
                    Integer32,
                hwSetEnvHumidityLowerLimit
                    Integer32,
                hwEnvHumiFatherEquipname
                    OCTET STRING,
                hwEnvHumiSensorOperStatus
                    INTEGER
            }

        hwEnvHumiSensorIndex OBJECT-TYPE
            SYNTAX Integer32
            MAX-ACCESS read-only
            STATUS current
            DESCRIPTION
                "Table index of the environment humility sensors.
                "
            ::= { hwEnvHumiSensorEntry 1 }

        hwEnvHumiEquipId OBJECT-TYPE
            SYNTAX Unsigned32
            MAX-ACCESS read-only
            STATUS current
            DESCRIPTION
                "Environment humility sensor ID"
            ::= { hwEnvHumiSensorEntry 2 }

        hwEnvHumiEquipName OBJECT-TYPE
            SYNTAX OCTET STRING (SIZE (0..63))
            MAX-ACCESS read-write
            STATUS current
            DESCRIPTION
                "Environment humility sensor name, of the character string type, is used to specify an environment humility sensor. 
                Users can configure it.Otherwise, the configured character can not be any other languages except English. "
            ::= { hwEnvHumiSensorEntry 3 }

        hwEnvHumidity OBJECT-TYPE
            SYNTAX Integer32 (0..100)
            MAX-ACCESS read-only
            STATUS current
            DESCRIPTION
                "Environment humility. It is an environment parameter collected in real time. 
                Value range: 0 to 100, 
                unit: %RH, 
                and the value is an integer (1). 
                If the value is 2147483647(0x7FFFFFFF), it indicates that the humidity sensor is not configured."
            ::= { hwEnvHumiSensorEntry 4 }

        hwSetEnvHumidityUpperLimit OBJECT-TYPE
            SYNTAX Integer32 (0..100)
            MAX-ACCESS read-write
            STATUS current
            DESCRIPTION
                "Upper threshold of the environment humility alarm, can be configured by users. 
                Value range: 0 to 100, 
                unit: %RH, 
                and the value is an integer (1).  
                If the value is 2147483647(0x7FFFFFFF), it indicates that the value is invalid."
            ::= { hwEnvHumiSensorEntry 5 }

        hwSetEnvHumidityLowerLimit OBJECT-TYPE
            SYNTAX Integer32 (0..100)
            MAX-ACCESS read-write
            STATUS current
            DESCRIPTION
                "Lower threshold of the environment humility alarm, can be configured by users. 
                Value range: 0 to 100, 
                unit: %RH, 
                and the value is an integer (1).  
                If the value is 2147483647(0x7FFFFFFF), it indicates that the value is invalid."
            ::= { hwEnvHumiSensorEntry 6 }

        hwEnvHumiFatherEquipname OBJECT-TYPE
            SYNTAX OCTET STRING
            MAX-ACCESS read-only
            STATUS current
            DESCRIPTION
                "Name of the parent device of the Humi equip"
            ::= { hwEnvHumiSensorEntry 10 }

        hwEnvHumiSensorOperStatus OBJECT-TYPE
            SYNTAX INTEGER
                {
                normal(1),
                humidityHigh(2),
                humidityLow(3),
                notInslot(4),
                alarmResume(254),
                unknown(255)
                }
            MAX-ACCESS read-only
            STATUS current
            DESCRIPTION
                "State of the site environment humidity sensor. It is an enumeration type: 
                  If the enumeration value is 1, it indicates that the site environment humidity sensor is in the normal state; 
                  If the enumeration value is 2, it indicates that the environment humidity sensor is over humidity; 
                  If the enumeration value is 3, it indicates that the environment humidity sensor is under humidity;
                  If the enumeration value is 4, it indicates that the environment humidity sensor is not in slot;
                  If the enumeration value is 254, it indicates that environment humidity alarm resume;   
                  If the enumeration value is 255, it indicates environment humidity sensor operation status unknown.  "
            ::= { hwEnvHumiSensorEntry 99 }

        hwSpareDigitalTable OBJECT-TYPE
            SYNTAX SEQUENCE OF HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 3 }

        hwSpareDigitalEntry OBJECT-TYPE
                        SYNTAX HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalIndex }
            ::= { hwSpareDigitalTable 1 }

        HwSpareDigitalEntry            ::= SEQUENCE {
                hwSpareDigitalIndex
                    Integer32,
                hwSpareDigitalEquipId
                    Unsigned32,
                hwSpareDigitalEquipName
                    OCTET STRING,
                hwSpareDigitalAlarmTension
                    INTEGER,
                hwSpareDigitalFatherEquipname
                    OCTET STRING,
                hwSpareDigitalOperStatus
                    INTEGER
            }

        hwSpareDigitalIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalEntry 1 }

        hwSpareDigitalEquipId OBJECT-TYPE
            SYNTAX Unsigned32
            MAX-ACCESS read-only
            STATUS current
            DESCRIPTION
                "Spare digital device ID. "
            ::= { hwSpareDigitalEntry 2 }

        hwSpareDigitalEquipName OBJECT-TYPE
            SYNTAX OCTET STRING (SIZE (0..8))
            MAX-ACCESS read-only
            STATUS current
            DESCRIPTION
                "Spare digital name, of the character string type, is used to specify Spare digitals. Users can configure it. Otherwise, the configured character can not be any other languages except English. "
            ::= { hwSpareDigitalEntry 3 }

        hwSpareDigitalAlarmTension OBJECT-TYPE
            SYNTAX INTEGER
                {
                open(0),
                close(1)
                }
            MAX-ACCESS read-write
            STATUS current
            DESCRIPTION
                "Spare digital alarm state. It is an enumeration value.  
                  If the value of the node is open, it indicates a low-tension alarm;
                  If the value of the node is close, it indicates a high-tension alarm. "
            ::= { hwSpareDigitalEntry 4 }

        hwSpareDigitalFatherEquipname OBJECT-TYPE
            SYNTAX OCTET STRING
            MAX-ACCESS read-only
            STATUS current
            DESCRIPTION
                "Name of the parent device of the Spare digital"
            ::= { hwSpareDigitalEntry 6 }

        hwSpareDigitalOperStatus OBJECT-TYPE
            SYNTAX INTEGER
                {
                normal(1),
                alarm(2),
                alarmResume(254),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 254, it indicates that spare digital alarm resume;  
                  If the enumeration value is 255, it indicates Spare digital operation status unknown."
            ::= { hwSpareDigitalEntry 99 }

        hwSpareDigitalOutputTable OBJECT-TYPE
            SYNTAX SEQUENCE OF HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 4 }

        hwSpareDigitalOutputEntry OBJECT-TYPE
                        SYNTAX HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalOutputIndex }
            ::= { hwSpareDigitalOutputTable 1 }

        HwSpareDigitalOutputEntry            ::= SEQUENCE {
                hwSpareDigitalOutputIndex
                    Integer32,
                hwSpareDigitalOutputEquipId
                    Unsigned32,
                hwSpareDigitalOutputEquipName
                    OCTET STRING,
                hwSetSpareDigitalOutputAlarmCondition
                    INTEGER,
                hwSpareDigitalOutputFatherEquipname
                    OCTET STRING,
                hwSpareDigitalOutputOperStatus
                    INTEGER
            }

        hwSpareDigitalOutputIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalOutputEntry 1 }

        hwSpareDigitalOutputEquipId OBJECT-TYPE
            SYNTAX Unsigned32
            MAX-ACCESS read-only
            STATUS current
            DESCRIPTION
                "Spare digital device ID."
            ::= { hwSpareDigitalOutputEntry 2 }

        hwSpareDigitalOutputEquipName OBJECT-TYPE
            SYNTAX OCTET STRING (SIZE (0..63))
            MAX-ACCESS read-only
            STATUS current
            DESCRIPTION
                "Spare digital name, of the character string type, is used to specify Spare digitals. Users can configure it. Otherwise, the configured character can not be any other languages except English. "
            ::= { hwSpareDigitalOutputEntry 3 }

        hwSetSpareDigitalOutputAlarmCondition OBJECT-TYPE
            SYNTAX INTEGER
                {
                open(1),
                close(2)
                }
            MAX-ACCESS read-write
            STATUS current
            DESCRIPTION
                "Spare digital alarm state. It is an enumeration value.  
                  If the value of the node is 1, it indicates a low-tension alarm;
                  If the value of the node is 2, it indicates a high-tension alarm. "
            ::= { hwSpareDigitalOutputEntry 4 }

        hwSpareDigitalOutputFatherEquipname OBJECT-TYPE
            SYNTAX OCTET STRING
            MAX-ACCESS read-only
            STATUS current
            DESCRIPTION
                "Name of the parent device of the Spare digital output "
            ::= { hwSpareDigitalOutputEntry 6 }

        hwSpareDigitalOutputOperStatus OBJECT-TYPE
            SYNTAX INTEGER
                {
                open(1),
                close(2),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 255, it indicates Spare digital operation status unknown."
            ::= { hwSpareDigitalOutputEntry 99 }

        hwTemp1Table OBJECT-TYPE
            SYNTAX SEQUENCE OF HwTemp1Entry
            MAX-ACCESS not-accessible
             STATUS current
             DESCRIPTION
                "Temp1 Table."
            ::= { hwEnvSensor 5 }

        hwTemp1Entry OBJECT-TYPE
                        SYNTAX HwTemp1Entry
            MAX-ACCESS not-accessible
             STATUS current
             DESCRIPTION
                "Temp1 Table."
            INDEX { hwTemp1Index }
            ::= { hwTemp1Table 1 }

        HwTemp1Entry            ::= SEQUENCE {
                hwTemp1Index
                    Integer32,
                hwTemp1EquipId
                    Unsigned32,
                hwTemp1EquipName
                    OCTET STRING,
                hwTemp1Value
                    Integer32,
                hwTemp1HighLimit
                    Integer32,
                hwTemp1LowLimit
                    Integer32,
                hwTemp1FatherEquipname
                    OCTET STRING,
                hwTemp1OperStatus
                    INTEGER
            }

        hwTemp1Index OBJECT-TYPE
            SYNTAX Integer32 (3394)
            MAX-ACCESS read-only
            STATUS current
            DESCRIPTION
                "Table index of the temp1 sensors. Value range: 1 to 256. Lines of the device list are restricted by the quantity of temp1 sensors (hwEnvHumiSensorsTotalQuantity). "
            ::= { hwTemp1Entry 1 }

        hwTemp1EquipId OBJECT-TYPE
            SYNTAX Unsigned32 (26000..26255)
            MAX-ACCESS read-only
            STATUS current
            DESCRIPTION
                "Temp1 sensor ID, can be configured by users. Value range: 026'000 to 026'255, in which the first digits indicate the device type and the last three digits indicate the device SN."
            ::= { hwTemp1Entry 2 }

        hwTemp1EquipName OBJECT-TYPE
            SYNTAX OCTET STRING (SIZE (0..63))
            MAX-ACCESS read-only
            STATUS current
            DESCRIPTION
                "Temp1 sensor name, of the character string type, is used to specify an temp1 sensor. Users can configure it. Otherwise, the configured character can not be any other languages except English."
            ::= { hwTemp1Entry 3 }

        hwTemp1Value OBJECT-TYPE
            SYNTAX Integer32 ( -40..125)
            MAX-ACCESS read-only
            STATUS current
            DESCRIPTION
                "Temp1. It is an environment parameter collected in real time. 
                Value range: -40 to +125, 
                unit: centigrade (degC), 
                and the value is an integer (1).  
                If the value is -1024, it indicates that the temperature sensor is not configured."
            ::= { hwTemp1Entry 4 }

        hwTemp1HighLimit OBJECT-TYPE
            SYNTAX Integer32 (25..80)
            MAX-ACCESS read-write
            STATUS current
            DESCRIPTION
                "Upper threshold of the temp1 alarm, can be configured by users. 
                Value range: 25 to 80, 
                unit: centigrade (degC), 
                and the value is an integer (1).  
                If the value is 2147483647(0x7FFFFFFF), it indicates that the value is invalid."
            ::= { hwTemp1Entry 5 }

        hwTemp1LowLimit OBJECT-TYPE
            SYNTAX Integer32 ( -20..20)
            MAX-ACCESS read-write
            STATUS current
            DESCRIPTION
                "Lower threshold of the temp1 alarm, can be configured by users. Value range: -20 to 20, unit: centigrade (degC), and the value is an integer (1).  If the value is 2147483647(0x7FFFFFFF), it indicates that the value is invalid."
            ::= { hwTemp1Entry 6 }

        hwTemp1FatherEquipname OBJECT-TYPE
            SYNTAX OCTET STRING
            MAX-ACCESS read-only
            STATUS current
            DESCRIPTION
                "Name of the parent device of the Temp1 sensors"
            ::= { hwTemp1Entry 7 }

        hwTemp1OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwTemp1Entry 99 }

        hwTemp2Table OBJECT-TYPE
            SYNTAX SEQUENCE OF HwTemp2Entry
            MAX-ACCESS not-accessible
             STATUS current
             DESCRIPTION
                "Temp2 Table."
            ::= { hwEnvSensor 6 }

        hwTemp2Entry OBJECT-TYPE
                        SYNTAX HwTemp2Entry
            MAX-ACCESS not-accessible
             STATUS current
             DESCRIPTION
                "Temp2 Table."
            INDEX { hwTemp2Index }
            ::= { hwTemp2Table 1 }

        HwTemp2Entry            ::= SEQUENCE {
                hwTemp2Index
                    Integer32,
                hwTemp2EquipId
                    Unsigned32,
                hwTemp2EquipName
                    OCTET STRING,
                hwTemp2Value
                    Integer32,
                hwTemp2HighLimit
                    Integer32,
                hwTemp2LowLimit
                    Integer32,
                hwTemp2FatherEquipname
                    OCTET STRING,
                hwTemp2OperStatus
                    INTEGER
            }

        hwTemp2Index OBJECT-TYPE
            SYNTAX Integer32 (3394)
            MAX-ACCESS read-only
            STATUS current
            DESCRIPTION
                "Table index of the temp2 sensors. 
                Value range: 1 to 256. 
                Lines of the device list are restricted by the quantity of temp2 sensors (hwEnvHumiSensorsTotalQuantity). "
            ::= { hwTemp2Entry 1 }

        hwTemp2EquipId OBJECT-TYPE
            SYNTAX Unsigned32 (27000..27255)
            MAX-ACCESS read-only
            STATUS current
            DESCRIPTION
                "Temp2 sensor ID, can be configured by users. Value range: 027'000 to 027'255, in which the first digits indicate the device type and the last three digits indicate the device SN."
            ::= { hwTemp2Entry 2 }

        hwTemp2EquipName OBJECT-TYPE
            SYNTAX OCTET STRING (SIZE (0..63))
            MAX-ACCESS read-only
            STATUS current
            DESCRIPTION
                "Temp2 sensor name, of the character string type, is used to specify an temp2 sensor. Users can configure it. Otherwise, the configured character can not be any other languages except English."
            ::= { hwTemp2Entry 3 }

        hwTemp2Value OBJECT-TYPE
            SYNTAX Integer32 ( -40..125)
            MAX-ACCESS read-only
            STATUS current
            DESCRIPTION
                "Temp2. It is an environment parameter collected in real time. 
                Value range: -40 to +125, 
                unit: centigrade (degC), 
                and the value is an integer (1).  
                If the value is -1024, it indicates that the temperature sensor is not configured."
            ::= { hwTemp2Entry 4 }

        hwTemp2HighLimit OBJECT-TYPE
            SYNTAX Integer32 (25..80)
            MAX-ACCESS read-write
            STATUS current
            DESCRIPTION
                "Upper threshold of the temp2 alarm, can be configured by users. 
                Value range: 25 to 80, 
                unit: centigrade (degC), 
                and the value is an integer (1).  
                If the value is 2147483647(0x7FFFFFFF), it indicates that the value is invalid."
            ::= { hwTemp2Entry 5 }

        hwTemp2LowLimit OBJECT-TYPE
            SYNTAX Integer32 ( -20..20)
            MAX-ACCESS read-write
            STATUS current
            DESCRIPTION
                "Lower threshold of the temp2 alarm, can be configured by users. 
                Value range: -20 to 20, 
                unit: centigrade (degC), 
                and the value is an integer (1).  
                If the value is 2147483647(0x7FFFFFFF), it indicates that the value is invalid."
            ::= { hwTemp2Entry 6 }

        hwTemp2FatherEquipname OBJECT-TYPE
            SYNTAX OCTET STRING
            MAX-ACCESS read-only
            STATUS current
            DESCRIPTION
                "Name of the parent device of the Temp2 sensors"
            ::= { hwTemp2Entry 7 }

        hwTemp2OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp2 sensor. It is an enumeration type: 
                  If the enumeration value is 1, it indicates that the site temp2 sensor is in the normal state; 
                  If the enumeration value is 2, it indicates that the temp2 sensor is over temperature; 
                  If the enumeration value is 3, it indicates that the temp2 sensor is under temperature; 
                  If the enumeration value is 4, it indicates that the temp2 sensor is not in slot;
                  If the enumeration value is 5, it indicates that the temp2 sensor is fault;
                  If the enumeration value is 254, it indicates that temp2 alarm resume; 
                  If the enumeration value is 255, it indicates temp2 sensor operation status unknown."
            ::= { hwTemp2Entry 99 }

        hwSmokeSensorTable OBJECT-TYPE
            SYNTAX SEQUENCE OF HwSmokeSensorEntry
            MAX-ACCESS not-accessible
             STATUS current
             DESCRIPTION
                "/"
            ::= { hwEnvSensor 13 }

        hwSmokeSensorEntry OBJECT-TYPE
                        SYNTAX HwSmokeSensorEntry
            MAX-ACCESS not-accessible
             STATUS current
             DESCRIPTION
                "/"
            INDEX { hwSmokeSensorIndex }
            ::= { hwSmokeSensorTable 1 }

        HwSmokeSensorEntry            ::= SEQUENCE {
                hwSmokeSensorIndex
                    Unsigned32,
                hwSmokeSensorEquipId
                    Unsigned32,
                hwSmokeEquipName
                    OCTET STRING,
                hwSmokeSensorStatus
                    INTEGER,
                hwSmokeSensorFatherEquipname
                    OCTET STRING,
                hwSmokeSensorReset
                    INTEGER
            }

        hwSmokeSensorIndex OBJECT-TYPE
            SYNTAX Unsigned32
            MAX-ACCESS read-only
            STATUS current
            DESCRIPTION
                "The smoke sensor equip Index."
            ::= { hwSmokeSensorEntry 1 }

        hwSmokeSensorEquipId OBJECT-TYPE
            SYNTAX Unsigned32
            MAX-ACCESS read-only
            STATUS current
            DESCRIPTION
                "/"
            ::= { hwSmokeSensorEntry 2 }

        hwSmokeEquipName OBJECT-TYPE
            SYNTAX OCTET STRING (SIZE (0..63))
            MAX-ACCESS read-only
            STATUS current
            DESCRIPTION
                "/"
            ::= { hwSmokeSensorEntry 3 }

        hwSmokeSensorStatus OBJECT-TYPE
            SYNTAX INTEGER
                {
                normal(0),
                alarm(1), 
                unknown(255)
                }
            MAX-ACCESS read-only
            STATUS current
            DESCRIPTION
                "The smoke sensor status, Enumeration meaning:
                normal(0),alarm(1), unknown(255)"
            ::= { hwSmokeSensorEntry 4 }

        hwSmokeSensorFatherEquipname OBJECT-TYPE
            SYNTAX OCTET STRING
            MAX-ACCESS read-only
            STATUS current
            DESCRIPTION
                "Name of the parent device of the Smoke Sensor"
            ::= { hwSmokeSensorEntry 5 }

        hwSmokeSensorReset OBJECT-TYPE
            SYNTAX INTEGER
                {
                reset(2),
                nullOper(255)
                }
            MAX-ACCESS read-write
            STATUS current
            DESCRIPTION
                "Smoke sensor reset. It manually controls clearance of the smoke sensor alarm, and this node is of the enumeration type. 
                If the enumeration value of the node is 1, it indicates that the reset of the smoke sensor is not required. 
                If the enumeration value of the node is 2, it indicates that the background controls the reset of the smoke sensor. 
                If the enumeration value of the node is 255, it indicates that the background controls the unknown of the smoke sensor. "
            ::= { hwSmokeSensorEntry 6 }

        hwWaterSensorTable OBJECT-TYPE
            SYNTAX SEQUENCE OF HwWaterSensorEntry
            MAX-ACCESS not-accessible
             STATUS current
             DESCRIPTION
                "/"
            ::= { hwEnvSensor 14 }

        hwWaterSensorEntry OBJECT-TYPE
                        SYNTAX HwWaterSensorEntry
            MAX-ACCESS not-accessible
             STATUS current
             DESCRIPTION
                "/"
            INDEX { hwWaterSensorIndex }
            ::= { hwWaterSensorTable 1 }

        HwWaterSensorEntry            ::= SEQUENCE {
                hwWaterSensorIndex
                    Unsigned32,
                hwWaterSensorEquipId
                    Unsigned32,
                hwWaterEquipName
                    OCTET STRING,
                hwWaterSensorStatus
                    INTEGER,
                hwWaterSensorFatherEquipname
                    OCTET STRING
            }

        hwWaterSensorIndex OBJECT-TYPE
            SYNTAX Unsigned32
            MAX-ACCESS read-only
            STATUS current
            DESCRIPTION
                "The water sensor equip Index."
            ::= { hwWaterSensorEntry 1 }

        hwWaterSensorEquipId OBJECT-TYPE
            SYNTAX Unsigned32
            MAX-ACCESS read-only
            STATUS current
            DESCRIPTION
                "/"
            ::= { hwWaterSensorEntry 2 }

        hwWaterEquipName OBJECT-TYPE
            SYNTAX OCTET STRING (SIZE (0..63))
            MAX-ACCESS read-only
            STATUS current
            DESCRIPTION
                "/"
            ::= { hwWaterSensorEntry 3 }

        hwWaterSensorStatus OBJECT-TYPE
            SYNTAX INTEGER
                {
                normal(0),
                alarm(1), 
                unknown(255)
                }
            MAX-ACCESS read-only
            STATUS current
            DESCRIPTION
                "The water sensor status, Enumeration meaning:
                normal(0),alarm(1), unknown(255)"
            ::= { hwWaterSensorEntry 4 }

        hwWaterSensorFatherEquipname OBJECT-TYPE
            SYNTAX OCTET STRING
            MAX-ACCESS read-only
            STATUS current
            DESCRIPTION
                "Name of the parent device of the Water Sensor"
            ::= { hwWaterSensorEntry 5 }

        hwDoorSensorTable OBJECT-TYPE
            SYNTAX SEQUENCE OF HwDoorSensorEntry
            MAX-ACCESS not-accessible
             STATUS current
             DESCRIPTION
                "/"
            ::= { hwEnvSensor 15 }

        hwDoorSensorEntry OBJECT-TYPE
                        SYNTAX HwDoorSensorEntry
            MAX-ACCESS not-accessible
             STATUS current
             DESCRIPTION
                "/"
            INDEX { hwDoorSensorIndex }
            ::= { hwDoorSensorTable 1 }

        HwDoorSensorEntry            ::= SEQUENCE {
                hwDoorSensorIndex
                    Unsigned32,
                hwDoorSensorEquipId
                    Unsigned32,
                hwDoorEquipName
                    OCTET STRING,
                hwDoorSensorStatus
                    INTEGER,
                hwDoorSensorFatherEquipname
                    OCTET STRING
            }

        hwDoorSensorIndex OBJECT-TYPE
            SYNTAX Unsigned32
            MAX-ACCESS read-only
            STATUS current
            DESCRIPTION
                "The door sensor equip Index."
            ::= { hwDoorSensorEntry 1 }

        hwDoorSensorEquipId OBJECT-TYPE
            SYNTAX Unsigned32
            MAX-ACCESS read-only
            STATUS current
            DESCRIPTION
                "/"
            ::= { hwDoorSensorEntry 2 }

        hwDoorEquipName OBJECT-TYPE
            SYNTAX OCTET STRING (SIZE (0..63))
            MAX-ACCESS read-only
            STATUS current
            DESCRIPTION
                "/"
            ::= { hwDoorSensorEntry 3 }

        hwDoorSensorStatus OBJECT-TYPE
            SYNTAX INTEGER
                {
                normal(0),
                alarm(1), 
                unknown(255)
                }
            MAX-ACCESS read-only
            STATUS current
            DESCRIPTION
                "The door sensor status"
            ::= { hwDoorSensorEntry 4 }

        hwDoorSensorFatherEquipname OBJECT-TYPE
            SYNTAX OCTET STRING
            MAX-ACCESS read-only
            STATUS current
            DESCRIPTION
                "Name of the parent device of the Door Sensor "
            ::= { hwDoorSensorEntry 5 }

        hwSiteInverters OBJECT IDENTIFIER ::= { hwSiteMonitorMIBObjects 9 }

        hwInverterGroup OBJECT IDENTIFIER ::= { hwSiteInverters 1 }

        hwInverterGroupId OBJECT-TYPE
            SYNTAX Unsigned32
            MAX-ACCESS read-only
            STATUS current
            DESCRIPTION
                "Inverter unit group ID. It is the unique ID of the Inverter unit group. 
                The first digits indicate the device type. The last three digits indicate the device SN. 
                If the last three digits are 000, it indicates a virtual device."
            ::= { hwInverterGroup 1 }

        hwInverterGroupName OBJECT-TYPE
            SYNTAX Unsigned32 (0..63
)
            MAX-ACCESS read-write
            STATUS current
            DESCRIPTION
                "Inverter unit group name, of the character string type, can be configured by users.Otherwise, the configured character can not be any other languages except English."
            ::= { hwInverterGroup 2 }

        hwInverterQuantity OBJECT-TYPE
            SYNTAX Unsigned32
            MAX-ACCESS read-only
            STATUS current
            DESCRIPTION
                "Total site intelligent Inverters. "
            ::= { hwInverterGroup 3 }

        hwInverter OBJECT IDENTIFIER ::= { hwSiteInverters 2 }

        hwInverterTable OBJECT-TYPE
            SYNTAX SEQUENCE OF HwInverterEntry
            MAX-ACCESS not-accessible
             STATUS current
             DESCRIPTION
                "/"
            ::= { hwInverter 1 }

        hwInverterEntry OBJECT-TYPE
                        SYNTAX HwInverterEntry
            MAX-ACCESS not-accessible
             STATUS current
             DESCRIPTION
                "/"
            INDEX { hwInverterIndex }
            ::= { hwInverterTable 1 }

        HwInverterEntry            ::= SEQUENCE {
                hwInverterIndex
                    Unsigned32,
                hwInverterEquipId
                    Unsigned32,
                hwInverterEquipName
                    OCTET STRING,
                hwInverterAcOutputVolt
                    Unsigned32,
                hwInverterAcOutputCurr
                    Unsigned32,
                hwInverterAcOutputFreq
                    Unsigned32,
                hwInverterAcOutputActivePower
                    Unsigned32,
                hwInverterAcOutputVA
                    Unsigned32,
                hwInverterAcInputVolt
                    Unsigned32,
                hwInverterAcInputCurr
                    Unsigned32,
                hwInverterAcInputFreq
                    Unsigned32,
                hwInverterAcInputActivePower
                    Unsigned32,
                hwInverterAcInputVA
                    Unsigned32,
                hwInverterDcInputVolt
                    Unsigned32,
                hwInverterDcInputCurr
                    Unsigned32,
                hwInverterDcInputPower
                    Unsigned32,
                hwInverterRevision
                    OCTET STRING,
                hwInverterPhaseNum
                    Unsigned32,
                hwInverterAcGroupNum
                    Unsigned32,
                hwInverterDcGroupNum
                    Unsigned32,
                hwInverterMajorAlarmNum
                    Unsigned32,
                hwInverterMinorAlarmNum
                    Unsigned32,
                hwInverterT2SSerialNum
                    Unsigned32,
                hwInverterModuleTemp
                    Integer32,
                hwInverterOperStatus
                    INTEGER,
                hwInverterRowStatus
                    RowStatus
            }

        hwInverterIndex OBJECT-TYPE
            SYNTAX Unsigned32 (1..256)
            MAX-ACCESS read-only
            STATUS current
            DESCRIPTION
                "Inverter table index,which value range:1 to 256.Lines of the device list are restricted by the quantity of Inverter."
            ::= { hwInverterEntry 1 }

        hwInverterEquipId OBJECT-TYPE
            SYNTAX Unsigned32 (18001..18255)
            MAX-ACCESS read-only
            STATUS current
            DESCRIPTION
                "Inverter device ID. Value range: 018'001 to 018'255, in which the first digits indicate the device type and the last three digits indicate the device SN. "
            ::= { hwInverterEntry 2 }

        hwInverterEquipName OBJECT-TYPE
            SYNTAX OCTET STRING (SIZE (0..63))
            MAX-ACCESS read-only
            STATUS current
            DESCRIPTION
                "Inverter name, of the character string type, is used to specify Inverters. Users can configure it.Otherwise, the configured character can not be any other languages except English. "
            ::= { hwInverterEntry 3 }

        hwInverterAcOutputVolt OBJECT-TYPE
            SYNTAX Unsigned32 (0..100000)
            MAX-ACCESS read-only
            STATUS current
            DESCRIPTION
                "Inverter AC Output voltage, 
                Value range: 0.0 to 10000.0.
                Unit: V.
                and the value is accurate to one decimal space (.1).  
                If the value is 2147483647(0x7FFFFFFF), it indicates that the value is invalid."
            ::= { hwInverterEntry 4 }

        hwInverterAcOutputCurr OBJECT-TYPE
            SYNTAX Unsigned32 (0..100000)
            MAX-ACCESS read-only
            STATUS current
            DESCRIPTION
                "Inverter AC Output current, 
                Value range: 0.0 to 10000.0.
                Unit: A.
                and the value is accurate to one decimal space (.1).  
                If the value is 2147483647(0x7FFFFFFF), it indicates that the value is invalid."
            ::= { hwInverterEntry 5 }

        hwInverterAcOutputFreq OBJECT-TYPE
            SYNTAX Unsigned32 (0..10000)
            MAX-ACCESS read-only
            STATUS current
            DESCRIPTION
                "Inverter AC Output frequency, 
                Value range: 0 to 10000. 
                Unit: Hz. 
                If the value is 2147483647(0x7FFFFFFF), it indicates that the value is invalid."
            ::= { hwInverterEntry 6 }

        hwInverterAcOutputActivePower OBJECT-TYPE
            SYNTAX Unsigned32 (0..10000000)
            MAX-ACCESS read-only
            STATUS current
            DESCRIPTION
                "Inverter AC Output power, 
                Value range: 0 to 10000000.
                Unit: W. 
                If the value is 2147483647(0x7FFFFFFF), it indicates that the value is invalid."
            ::= { hwInverterEntry 7 }

        hwInverterAcOutputVA OBJECT-TYPE
            SYNTAX Unsigned32 (0..100000)
            MAX-ACCESS read-only
            STATUS current
            DESCRIPTION
                "Inverter AC Output power, 
                Value range: 0.0 to 100000.0.
                Unit: VA.
                and the value is accurate to one decimal space (.1).  
                If the value is 2147483647(0x7FFFFFFF), it indicates that the value is invalid."
            ::= { hwInverterEntry 8 }

        hwInverterAcInputVolt OBJECT-TYPE
            SYNTAX Unsigned32 (0..100000)
            MAX-ACCESS read-only
            STATUS current
            DESCRIPTION
                "Inverter AC Input voltage, 
                Value range: 0.0 to 10000.0.
                Unit: V.
                and the value is accurate to one decimal space (.1).  
                If the value is 2147483647(0x7FFFFFFF), it indicates that the value is invalid."
            ::= { hwInverterEntry 9 }

        hwInverterAcInputCurr OBJECT-TYPE
            SYNTAX Unsigned32 (0..100000)
            MAX-ACCESS read-only
            STATUS current
            DESCRIPTION
                "Inverter AC Input current, 
                Value range: 0.0 to 10000.0.
                Unit: A.
                and the value is accurate to one decimal space (.1).  
                If the value is 2147483647(0x7FFFFFFF), it indicates that the value is invalid."
            ::= { hwInverterEntry 10 }

        hwInverterAcInputFreq OBJECT-TYPE
            SYNTAX Unsigned32 (0..10000)
            MAX-ACCESS read-only
            STATUS current
            DESCRIPTION
                "Inverter AC Input frequency, 
                Value range: 0 to 10000. 
                Unit: Hz. 
                If the value is 2147483647(0x7FFFFFFF), it indicates that the value is invalid."
            ::= { hwInverterEntry 11 }

        hwInverterAcInputActivePower OBJECT-TYPE
            SYNTAX Unsigned32 (0..10000000)
            MAX-ACCESS read-only
            STATUS current
            DESCRIPTION
                "Inverter AC Input power, 
                Value range: 0 to 10000000.
                Unit: W. 
                If the value is 2147483647(0x7FFFFFFF), it indicates that the value is invalid."
            ::= { hwInverterEntry 12 }

        hwInverterAcInputVA OBJECT-TYPE
            SYNTAX Unsigned32 (0..100000)
            MAX-ACCESS read-only
            STATUS current
            DESCRIPTION
                "Inverter AC Input power, 
                Value range: 0.0 to 10000.0.
                Unit: VA.
                and the value is accurate to one decimal space (.1).  
                If the value is 2147483647(0x7FFFFFFF), it indicates that the value is invalid."
            ::= { hwInverterEntry 13 }

        hwInverterDcInputVolt OBJECT-TYPE
            SYNTAX Unsigned32 (0..100000)
            MAX-ACCESS read-only
            STATUS current
            DESCRIPTION
                "Inverter DC Input voltage, 
                Value range: 0.0 to 10000.0.
                Unit: V.
                and the value is accurate to one decimal space (.1).  
                If the value is 2147483647(0x7FFFFFFF), it indicates that the value is invalid."
            ::= { hwInverterEntry 14 }

        hwInverterDcInputCurr OBJECT-TYPE
            SYNTAX Unsigned32 (0..100000)
            MAX-ACCESS read-only
            STATUS current
            DESCRIPTION
                "Inverter DC Input current, 
                Value range: 0 to 10000. 
                Unit: A.
                and the value is accurate to one decimal space (.1).  
                If the value is 2147483647(0x7FFFFFFF), it indicates that the value is invalid."
            ::= { hwInverterEntry 15 }

        hwInverterDcInputPower OBJECT-TYPE
            SYNTAX Unsigned32 (0..10000000)
            MAX-ACCESS read-only
            STATUS current
            DESCRIPTION
                "Inverter DC Input power, 
                Value range: 0 to 10000000.
                Unit: W. 
                If the value is 2147483647(0x7FFFFFFF), it indicates that the value is invalid."
            ::= { hwInverterEntry 16 }

        hwInverterRevision OBJECT-TYPE
            SYNTAX OCTET STRING (SIZE (0..63))
            MAX-ACCESS read-only
            STATUS current
            DESCRIPTION
                "Inverter software version number."
            ::= { hwInverterEntry 17 }

        hwInverterPhaseNum OBJECT-TYPE
            SYNTAX Unsigned32 (0..10000)
            MAX-ACCESS read-only
            STATUS current
            DESCRIPTION
                "Inverter Number of the phase module, Value range: 0 to 10000.   If the value is 2147483647(0x7FFFFFFF), it indicates that the value is invalid."
            ::= { hwInverterEntry 18 }

        hwInverterAcGroupNum OBJECT-TYPE
            SYNTAX Unsigned32 (0..10000)
            MAX-ACCESS read-only
            STATUS current
            DESCRIPTION
                "Inverter Number of AC group, 
                Value range: 0 to 10000.  
                If the value is 2147483647(0x7FFFFFFF), it indicates that the value is invalid."
            ::= { hwInverterEntry 19 }

        hwInverterDcGroupNum OBJECT-TYPE
            SYNTAX Unsigned32 (0..10000)
            MAX-ACCESS read-only
            STATUS current
            DESCRIPTION
                "Inverter Number of DC group, 
                Value range: 0 to 10000.  
                If the value is 2147483647(0x7FFFFFFF), it indicates that the value is invalid."
            ::= { hwInverterEntry 20 }

        hwInverterMajorAlarmNum OBJECT-TYPE
            SYNTAX Unsigned32 (0..10000)
            MAX-ACCESS read-only
            STATUS current
            DESCRIPTION
                "Inverter Number of Major alarm, 
                Value range: 0 to 10000.  
                If the value is 2147483647(0x7FFFFFFF), it indicates that the value is invalid."
            ::= { hwInverterEntry 21 }

        hwInverterMinorAlarmNum OBJECT-TYPE
            SYNTAX Unsigned32 (0..10000)
            MAX-ACCESS read-only
            STATUS current
            DESCRIPTION
                "Inverter Number of Minor alarm, 
                Value range: 0 to 10000.  
                If the value is 2147483647(0x7FFFFFFF), it indicates that the value is invalid."
            ::= { hwInverterEntry 22 }

        hwInverterT2SSerialNum OBJECT-TYPE
            SYNTAX Unsigned32 (0..4294967295)
            MAX-ACCESS read-only
            STATUS current
            DESCRIPTION
                "Inverter T2S serial number, 
                Value range: 0 to 4294967295.  
                If the value is 4294967295(0x7FFFFFFF), it indicates that the value is invalid."
            ::= { hwInverterEntry 23 }

        hwInverterModuleTemp OBJECT-TYPE
            SYNTAX Integer32 (-300..10000)
            MAX-ACCESS read-only
            STATUS current
            DESCRIPTION
                "Inverter module Temperature,
                Value range: -300 to 10000. 
                Unit: degC.  
                If the value is 2147483647(0x7FFFFFFF), it indicates that the value is invalid."
            ::= { hwInverterEntry 24 }

        hwInverterOperStatus OBJECT-TYPE
            SYNTAX INTEGER
                {
                normal(1),
                alarm(2),
                alarmResume(254),
                unknow(255)
                }
            MAX-ACCESS read-only
            STATUS current
            DESCRIPTION
                "State of the Inverter. It is an enumeration type: 
                If the enumeration value is 1, it indicates that the Inverter is in the normal state;
                If the enumeration value is 2, it indicates that the Inverter is in the alarm state;  
                If the enumeration value is 254, it indicates that the Inverter is in the resume state;   
                If the enumeration value is 255, it indicates Inverter operation status unknown. "
            ::= { hwInverterEntry 99 }

        hwInverterRowStatus OBJECT-TYPE
            SYNTAX RowStatus
            MAX-ACCESS read-create
            STATUS current
            DESCRIPTION
                "RowStatus of Inverter table."
            ::= { hwInverterEntry 100 }

        hwSiteCoolingDevices OBJECT IDENTIFIER ::= { hwSiteMonitorMIBObjects 10 }

        hwCoolingDevicesGroup OBJECT IDENTIFIER ::= { hwSiteCoolingDevices 1 }

        hwCoolingDevicesEquipId OBJECT-TYPE
            SYNTAX Integer32 (19001..19255)
            MAX-ACCESS read-only
            STATUS current
            DESCRIPTION
                "CoolingDevices unit group ID. Value range: 019'001 to 019'255, in which the first digits indicate the device type and the last three digits indicate the device SN. "
            ::= { hwCoolingDevicesGroup 1 }

        hwCoolingDevicesEquipName OBJECT-TYPE
            SYNTAX OCTET STRING (SIZE (0..63))
            MAX-ACCESS read-write
            STATUS current
            DESCRIPTION
                "CoolingDevices unit group name, of the character string type, can be configured by users.
                Otherwise, the configured character can not be any other languages except English."
            ::= { hwCoolingDevicesGroup 2 }

        hwCoolingDevicesMode OBJECT-TYPE
            SYNTAX INTEGER
                {
                fanOnly(1),
                acOnly(2),
                smartMode(3),
                unknown(255)
                }
            MAX-ACCESS read-write
            STATUS current
            DESCRIPTION
                "State of the CoolingDevices TC mode. It is an enumeration type: 
                If the enumeration value is 1, it indicates that the CoolingDeviecs is in fanOnly state;
                If the enumeration value is 2, it indicates that the CoolingDeviecs is in acOnly state;
                If the enumeration value is 3, it indicates that the CoolingDeviecs is in smartMode state;
                If the enumeration value is 255, it indicates Inverter operation status unknown. "
            ::= { hwCoolingDevicesGroup 3 }

        hwCoolingDevicesHighTempAlarmTreshold OBJECT-TYPE
            SYNTAX Integer32 (25..80)
            MAX-ACCESS read-write
            STATUS current
            DESCRIPTION
                "CoolingDevices high temp alarm tres, 
                Value range: 25 to 80 
                Unit: degC.
                and the value is an integer (1). 
                If the value is 2147483647(0x7FFFFFFF), it indicates that the value is invalid."
            ::= { hwCoolingDevicesGroup 4 }

        hwCoolingDevicesHighTempAlarmClearTreshold OBJECT-TYPE
            SYNTAX Integer32 (25..80)
            MAX-ACCESS read-write
            STATUS current
            DESCRIPTION
                "CoolingDevices high temp alarm clear tres, 
                Value range: 25 to 80 
                Unit: degC.
                and the value is an integer (1).  
                If the value is 2147483647(0x7FFFFFFF), it indicates that the value is invalid."
            ::= { hwCoolingDevicesGroup 5 }

        hwCoolingDevicesExpelHidry OBJECT-TYPE
            SYNTAX INTEGER
                {
                no(1),
                yes(2)
                }
            MAX-ACCESS read-write
            STATUS current
            DESCRIPTION
                "State of the CoolingDevices expel hidry. It is an enumeration type: 
                If the enumeration value is 1, it indicates that the CoolingDeviecs is in no state;
                If the enumeration value is 2, it indicates that the CoolingDeviecs is in yes state;
                "
            ::= { hwCoolingDevicesGroup 6 }

        hwCoolingDevicesEquip OBJECT IDENTIFIER ::= { hwSiteCoolingDevices 2 }

        hwFanTable OBJECT-TYPE
            SYNTAX SEQUENCE OF HwFanEntry
            MAX-ACCESS not-accessible
             STATUS current
             DESCRIPTION
                "/"
            ::= { hwCoolingDevicesEquip 1 }

        hwFanEntry OBJECT-TYPE
                        SYNTAX HwFanEntry
            MAX-ACCESS not-accessible
             STATUS current
             DESCRIPTION
                "/"
            INDEX { hwFanIndex }
            ::= { hwFanTable 1 }

        HwFanEntry            ::= SEQUENCE {
                hwFanIndex
                    Unsigned32,
                hwFanEquipId
                    Unsigned32,
                hwFanEquipName
                    OCTET STRING,
                hwFanCtrlMode
                    INTEGER,
                hwFan1Status
                    INTEGER,
                hwFan2Status
                    INTEGER,
                hwFan3Status
                    INTEGER,
                hwFan4Status
                    INTEGER,
                hwFan1Speed
                    Integer32,
                hwFan2Speed
                    Integer32,
                hwFan3Speed
                    Integer32,
                hwFan4Speed
                    Integer32,
                hwFanFatherEquipName
                    OCTET STRING,
                hwFanOperStatus
                    INTEGER,
                hwFanRowStatus
                    RowStatus
            }

        hwFanIndex OBJECT-TYPE
            SYNTAX Unsigned32 (1..256)
            MAX-ACCESS read-only
            STATUS current
            DESCRIPTION
                "Fan table index,which 
                value range: 1 to 256.
                Lines of the device list are restricted by the quantity of Fan."
            ::= { hwFanEntry 1 }

        hwFanEquipId OBJECT-TYPE
            SYNTAX Unsigned32 (20001..20255)
            MAX-ACCESS read-only
            STATUS current
            DESCRIPTION
                "Fan device ID. Value range: 020'001 to 020'255, in which the first digits indicate the device type and the last three digits indicate the device SN. "
            ::= { hwFanEntry 2 }

        hwFanEquipName OBJECT-TYPE
            SYNTAX OCTET STRING (SIZE (0..63))
            MAX-ACCESS read-only
            STATUS current
            DESCRIPTION
                "Fan name, of the character string type, is used to specify Fans. Users can configure it.
                Otherwise, the configured character can not be any other languages except English. "
            ::= { hwFanEntry 3 }

        hwFanCtrlMode OBJECT-TYPE
            SYNTAX INTEGER
                {
                autoControl(1),
                manualControl(2),
                other(3)
                }
            MAX-ACCESS read-write
            STATUS current
            DESCRIPTION
                "State of the Fan ctrl mode. It is an enumeration type: 
                If the enumeration value is 1, it indicates that the fan is in autoControl state;
                If the enumeration value is 2, it indicates that the fan is in manualControl state;
                If the enumeration value is 3, it indicates that the fan is in other state;"
            ::= { hwFanEntry 4 }

        hwFan1Status OBJECT-TYPE
            SYNTAX INTEGER
                {
                normal(1),
                fault(2),
                inexistent(3),
                unknown(255)
                }
            MAX-ACCESS read-only
            STATUS current
            DESCRIPTION
                "State of the Fan1 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 5 }

        hwFan2Status OBJECT-TYPE
            SYNTAX INTEGER
                {
                normal(1),
                fault(2),
                inexistent(3),
                unknown(255)
                }
            MAX-ACCESS read-only
            STATUS current
            DESCRIPTION
                "State of the Fan2 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 6 }

        hwFan3Status OBJECT-TYPE
            SYNTAX INTEGER
                {
                normal(1),
                fault(2),
                inexistent(3),
                unknown(255)
                }
            MAX-ACCESS read-only
            STATUS current
            DESCRIPTION
                "State of the Fan3 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 7 }

        hwFan4Status OBJECT-TYPE
            SYNTAX INTEGER
                {
                normal(1),
                fault(2),
                inexistent(3),
                unknown(255)
                }
            MAX-ACCESS read-only
            STATUS current
            DESCRIPTION
                "State of the Fan4 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 8 }

        hwFan1Speed OBJECT-TYPE
            SYNTAX Integer32 (0..10000)
            MAX-ACCESS read-only
            STATUS current
            DESCRIPTION
                "Fan1 speed, 
                Value range: 0 to 10000.
                Unit: rpm.
                the value is an integer (1). 
                If the value is 2147483647(0x7FFFFFFF), it indicates that the value is invalid."
            ::= { hwFanEntry 9 }

        hwFan2Speed OBJECT-TYPE
            SYNTAX Integer32 (0..10000)
            MAX-ACCESS read-only
            STATUS current
            DESCRIPTION
                "Fan2 speed, 
                Value range: 0 to 10000.
                Unit: rpm.
                the value is an integer (1). 
                If the value is 2147483647(0x7FFFFFFF), it indicates that the value is invalid."
            ::= { hwFanEntry 10 }

        hwFan3Speed OBJECT-TYPE
            SYNTAX Integer32 (0..10000)
            MAX-ACCESS read-only
            STATUS current
            DESCRIPTION
                "Fan3 speed, 
                Value range: 0 to 10000.
                Unit: rpm.
                the value is an integer (1).
                 If the value is 2147483647(0x7FFFFFFF), it indicates that the value is invalid."
            ::= { hwFanEntry 11 }

        hwFan4Speed OBJECT-TYPE
            SYNTAX Integer32 (0..10000)
            MAX-ACCESS read-only
            STATUS current
            DESCRIPTION
                "Fan4 speed, 
                Value range: 0 to 10000.
                Unit: rpm.
                the value is an integer (1).
                If the value is 2147483647(0x7FFFFFFF), it indicates that the value is invalid."
            ::= { hwFanEntry 12 }

        hwFanFatherEquipName OBJECT-TYPE
            SYNTAX OCTET STRING (SIZE (0..63))
            MAX-ACCESS read-only
            STATUS current
            DESCRIPTION
                " Father device name of the fan equip. "
            ::= { hwFanEntry 14 }

        hwFanOperStatus OBJECT-TYPE
            SYNTAX INTEGER
                {
                normal(1),
                fault(2),
                alarmResume(254),
                unknow(255)
                }
            MAX-ACCESS read-only
            STATUS current
            DESCRIPTION
                "State of the fan. It is an enumeration type: 
                If the enumeration value is 1, it indicates that the Inverter is in the normal state;
                If the enumeration value is 2, it indicates that the Inverter is in the fault state;  
                If the enumeration value is 254, it indicates that the Inverter is in the resume state;   
                If the enumeration value is 255, it indicates Inverter operation status unknown. "
            ::= { hwFanEntry 99 }

        hwFanRowStatus OBJECT-TYPE
            SYNTAX RowStatus
            MAX-ACCESS read-create
            STATUS current
            DESCRIPTION
                "RowStatus fo fan table."
            ::= { hwFanEntry 100 }

        hwDcAirConditionTable OBJECT-TYPE
            SYNTAX SEQUENCE OF HwDcAirConditionEntry
            MAX-ACCESS not-accessible
             STATUS current
             DESCRIPTION
                ""
            ::= { hwCoolingDevicesEquip 2 }

        hwDcAirConditionEntry OBJECT-TYPE
                        SYNTAX HwDcAirConditionEntry
            MAX-ACCESS not-accessible
             STATUS current
             DESCRIPTION
                ""
            INDEX { hwDcAirIndex }
            ::= { hwDcAirConditionTable 1 }

        HwDcAirConditionEntry            ::= SEQUENCE {
                hwDcAirIndex
                    Unsigned32,
                hwDcAirEquipId
                    Unsigned32,
                hwDcAirEquipName
                    OCTET STRING,
                hwDcAirCtrlMode
                    INTEGER,
                hwDcAirCtrlOnOff
                    INTEGER,
                hwDcAirRunStatus
                    INTEGER,
                hwDcAirCompressorRunStatus
                    INTEGER,
                hwDcAirInnrFanSpeed
                    Integer32,
                hwDcAirOuterFanSpeed
                    Integer32,
                hwDcAirCompressorRunTime
                    Integer32,
                hwDcAirRunTime
                    Integer32,
                hwDcAirEnterChannelTemp
                    Integer32,
                hwDcAirPowerOnTempPoint
                    Integer32,
                hwDcAirPowerOffTempPoint
                    Integer32,
                hwAcOffEnergySaving
                    INTEGER,
                hwDcAirPowerOnAcOffPoint
                    Integer32,
                hwDcAirPowerOffAcOffPoint
                    Integer32,
                hwDcAirEquipAddress
                    Unsigned32,
                hwDcAirFatherEquipName
                    OCTET STRING,
                hwDcAirOperStatus
                    INTEGER,
                hwDcAirRowStatus
                    RowStatus
            }

        hwDcAirIndex OBJECT-TYPE
            SYNTAX Unsigned32
            MAX-ACCESS read-only
            STATUS current
            DESCRIPTION
                "Dc aircondition table index"
            ::= { hwDcAirConditionEntry 1 }

        hwDcAirEquipId OBJECT-TYPE
            SYNTAX Unsigned32
            MAX-ACCESS read-only
            STATUS current
            DESCRIPTION
                "Dc aircondition device ID. "
            ::= { hwDcAirConditionEntry 2 }

        hwDcAirEquipName OBJECT-TYPE
            SYNTAX OCTET STRING (SIZE (0..63))
            MAX-ACCESS read-only
            STATUS current
            DESCRIPTION
                "Dc aircondition name, of the character string type, is used to specify Fans. Users can configure it.
                Otherwise, the configured character can not be any other languages except English. "
            ::= { hwDcAirConditionEntry 3 }

        hwDcAirCtrlMode OBJECT-TYPE
            SYNTAX INTEGER
                {
                autoControl(1),
                manualControl(2),
                unknown(255)
                }
            MAX-ACCESS read-write
            STATUS current
            DESCRIPTION
                "State of the Dc aircondition ctrl mode. It is an enumeration type: 
                If the enumeration value is 1, it indicates that the Dc aircondition is in autoControl state;
                If the enumeration value is 2, it indicates that the Dc aircondition is in manualControl state;
                If the enumeration value is 255, it indicates that the Dc aircondition is in unknown state;"
            ::= { hwDcAirConditionEntry 4 }

        hwDcAirCtrlOnOff OBJECT-TYPE
            SYNTAX INTEGER
                {
                on(1),
                off(2)
                }
            MAX-ACCESS read-write
            STATUS current
            DESCRIPTION
                "State of the Dc aircondition control on or off. It is an enumeration type: 
                If the enumeration value is 1, it indicates that the Dc aircondition is in on state;
                If the enumeration value is 2, it indicates that the Dc aircondition is in off state;"
            ::= { hwDcAirConditionEntry 5 }

        hwDcAirRunStatus OBJECT-TYPE
            SYNTAX INTEGER
                {
                standby(1),
                run(2),
                fault(3),
                unknown(255)
                }
            MAX-ACCESS read-only
            STATUS current
            DESCRIPTION
                "State of the Dc aircondition run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is other state."
            ::= { hwDcAirConditionEntry 6 }

        hwDcAirCompressorRunStatus OBJECT-TYPE
            SYNTAX INTEGER
                {
                standby(1),
                run(2),
                fault(3),
                unknown(255)
                }
            MAX-ACCESS read-only
            STATUS current
            DESCRIPTION
                "State of the Dc air compressor run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is unknown state."
            ::= { hwDcAirConditionEntry 7 }

        hwDcAirInnrFanSpeed OBJECT-TYPE
            SYNTAX Integer32 (0..10000)
            MAX-ACCESS read-only
            STATUS current
            DESCRIPTION
                "Dc aircondition innr speed, 
                Value range: 0 to 10000.
                Unit: rpm,
                and the value is an integer (1).
                If the value is 2147483647(0x7FFFFFFF), it indicates that the value is invalid."
            ::= { hwDcAirConditionEntry 8 }

        hwDcAirOuterFanSpeed OBJECT-TYPE
            SYNTAX Integer32 (0..10000)
            MAX-ACCESS read-only
            STATUS current
            DESCRIPTION
                "Dc aircondition outer speed, 
                Value range: 0.0 to 10000.0.
                Unit: rpm,
                and the value is an integer (1).
                If the value is 2147483647(0x7FFFFFFF), it indicates that the value is invalid."
            ::= { hwDcAirConditionEntry 9 }

        hwDcAirCompressorRunTime OBJECT-TYPE
            SYNTAX Integer32 (0..175200)
            MAX-ACCESS read-only
            STATUS current
            DESCRIPTION
                "Dc aircondition compressor run time, 
                Value range: 0 to 175200.
                Unit: h,
                the value is an integer (1). 
                If the value is 2147483647(0x7FFFFFFF), it indicates that the value is invalid."
            ::= { hwDcAirConditionEntry 10 }

        hwDcAirRunTime OBJECT-TYPE
            SYNTAX Integer32 (0..175200)
            MAX-ACCESS read-only
            STATUS current
            DESCRIPTION
                "Dc aircondition run time, 
                Value range: 0 to 175200.
                Unit: H,
                the value is an integer (1). 
                If the value is 2147483647(0x7FFFFFFF), it indicates that the value is invalid."
            ::= { hwDcAirConditionEntry 11 }

        hwDcAirEnterChannelTemp OBJECT-TYPE
            SYNTAX Integer32 ( -50..100)
            MAX-ACCESS read-only
            STATUS current
            DESCRIPTION
                "Dc aircondition enter channel temperature, 
                Value range:-50 to 100.
                Unit: degC.
                and the value is an integer (1). 
                If the value is 2147483647(0x7FFFFFFF), it indicates that the value is invalid."
            ::= { hwDcAirConditionEntry 13 }

        hwDcAirPowerOnTempPoint OBJECT-TYPE
            SYNTAX Integer32 ( -200..800)
            MAX-ACCESS read-write
            STATUS current
            DESCRIPTION
                "Dc aircondition power on temperature point,
                Value range:-200 to 800.
                Unit: degC.
                the value is an integer (1).  
                If the value is 2147483647(0x7FFFFFFF), it indicates that the value is invalid."
            ::= { hwDcAirConditionEntry 14 }

        hwDcAirPowerOffTempPoint OBJECT-TYPE
            SYNTAX Integer32 ( -200..800)
            MAX-ACCESS read-write
            STATUS current
            DESCRIPTION
                "Dc aircondition power off temperature point, 
                Value range:-200 to 800 
                Unit: degC.
                the value is an integer (1).  
                If the value is 2147483647(0x7FFFFFFF), it indicates that the value is invalid."
            ::= { hwDcAirConditionEntry 15 }

        hwAcOffEnergySaving OBJECT-TYPE
            SYNTAX INTEGER
                {
                disable(1),
                enable(2)
                }
            MAX-ACCESS read-write
            STATUS current
            DESCRIPTION
                "State of the Dc air energy saving status. It is an enumeration type: 
                If the enumeration value is 1, it indicates that the Dc aircondition is in disable state;
                If the enumeration value is 2, it indicates that the Dc aircondition is in enable state;"
            ::= { hwDcAirConditionEntry 17 }

        hwDcAirPowerOnAcOffPoint OBJECT-TYPE
            SYNTAX Integer32 (40..45)
            MAX-ACCESS read-write
            STATUS current
            DESCRIPTION
                "Dc aircondition power on ac fail temperature point, 
                Value range: 40 to 45.
                Unit: degC.
                and the value is an integer (1). 
                If the value is 2147483647(0x7FFFFFFF), it indicates that the value is invalid."
            ::= { hwDcAirConditionEntry 18 }

        hwDcAirPowerOffAcOffPoint OBJECT-TYPE
            SYNTAX Integer32 ( 35..40)
            MAX-ACCESS read-write
            STATUS current
            DESCRIPTION
                "Dc aircondition power off ac fail temperature point, 
                Value range: 35 to 40.
                Unit: degC.
                and the value is an integer (1).  
                If the value is 2147483647(0x7FFFFFFF), it indicates that the value is invalid."
            ::= { hwDcAirConditionEntry 19 }

        hwDcAirEquipAddress OBJECT-TYPE
            SYNTAX Unsigned32 (0..255)
            MAX-ACCESS read-only
            STATUS current
            DESCRIPTION
                " DC Air Device address
                And the value is an integer (1)."
            ::= { hwDcAirConditionEntry 21 }

        hwDcAirFatherEquipName OBJECT-TYPE
            SYNTAX OCTET STRING (SIZE (0..63))
            MAX-ACCESS read-only
            STATUS current
            DESCRIPTION
                " Father device name of the DC Air equip. "
            ::= { hwDcAirConditionEntry 22 }

        hwDcAirOperStatus OBJECT-TYPE
            SYNTAX INTEGER
                {
                standby(1),
                run(2),
                fault(3),
                alarmResume(254),
                unknown(255)
                }
            MAX-ACCESS read-only
            STATUS current
            DESCRIPTION
                "State of the dc aircondition. It is an enumeration type: 
                If the enumeration value is 1, it indicates that the Inverter is in the standby state;
                If the enumeration value is 2, it indicates that the Inverter is in the run state;  
                If the enumeration value is 3, it indicates that the Inverter is in the fault state;
                If the enumeration value is 254, it indicates that the Inverter is in the resume state;     
                If the enumeration value is 255, it indicates Inverter operation status unknown. "
            ::= { hwDcAirConditionEntry 99 }

        hwDcAirRowStatus OBJECT-TYPE
            SYNTAX RowStatus
            MAX-ACCESS read-create
            STATUS current
            DESCRIPTION
                "RowStatus fo dc aircondition table."
            ::= { hwDcAirConditionEntry 100 }

        hwSiteAcAmmeters OBJECT IDENTIFIER ::= { hwSiteMonitorMIBObjects 11 }

        hwSiteAcAmmeterEquip OBJECT IDENTIFIER ::= { hwSiteAcAmmeters 2 }

        hwSiteAcAmmeterTable OBJECT-TYPE
            SYNTAX SEQUENCE OF HwSiteAcAmmeterEntry
            MAX-ACCESS not-accessible
             STATUS current
             DESCRIPTION
                "/"
            ::= { hwSiteAcAmmeterEquip 1 }

        hwSiteAcAmmeterEntry OBJECT-TYPE
                        SYNTAX HwSiteAcAmmeterEntry
            MAX-ACCESS not-accessible
             STATUS current
             DESCRIPTION
                "/"
            INDEX { hwAcAmmeterIndex }
            ::= { hwSiteAcAmmeterTable 1 }

        HwSiteAcAmmeterEntry            ::= SEQUENCE {
                hwAcAmmeterIndex
                    Unsigned32,
                hwAcAmmeterEquipId
                    Unsigned32,
                hwAcAmmeterEquipName
                    OCTET STRING,
                hwAcAmmeterFrequency
                    Unsigned32,
                hwAcAmmeterPhaseL1Voltage
                    Unsigned32,
                hwAcAmmeterPhaseL2Voltage
                    Unsigned32,
                hwAcAmmeterPhaseL3Voltage
                    Unsigned32,
                hwAcAmmeterSetChannelNum
                    Unsigned32,
                hwAcAmmeterClear
                    INTEGER,
                hwAcAmmeterType
                    Unsigned32,
                hwAcAmmeterVersion
                    OCTET STRING,
                hwAcAmmeterPhaseL1CurrentCH1
                    Unsigned32,
                hwAcAmmeterPhaseL2CurrentCH1
                    Unsigned32,
                hwAcAmmeterPhaseL3CurrentCH1
                    Unsigned32,
                hwAcAmmeterTotalActivePowerCH1
                    Integer32,
                hwAcAmmeterTotalPowerFactorCH1
                    Integer32,
                hwAcAmmeterTotalActiveEngryAccCH1
                    Unsigned32,
                hwAcAmmeterPhaseL1CurrentCH2
                    Unsigned32,
                hwAcAmmeterPhaseL2CurrentCH2
                    Unsigned32,
                hwAcAmmeterPhaseL3CurrentCH2
                    Unsigned32,
                hwAcAmmeterTotalActivePowerCH2
                    Integer32,
                hwAcAmmeterTotalPowerFactorCH2
                    Integer32,
                hwAcAmmeterTotalActiveEngryAccCH2
                    Unsigned32,
                hwAcAmmeterPhaseL1CurrentCH3
                    Unsigned32,
                hwAcAmmeterPhaseL2CurrentCH3
                    Unsigned32,
                hwAcAmmeterPhaseL3CurrentCH3
                    Unsigned32,
                hwAcAmmeterTotalActivePowerCH3
                    Integer32,
                hwAcAmmeterTotalPowerFactorCH3
                    Integer32,
                hwAcAmmeterTotalActiveEngryAccCH3
                    Unsigned32,
                hwAcAmmeterPhaseL1CurrentCH4
                    Unsigned32,
                hwAcAmmeterPhaseL2CurrentCH4
                    Unsigned32,
                hwAcAmmeterPhaseL3CurrentCH4
                    Unsigned32,
                hwAcAmmeterTotalActivePowerCH4
                    Integer32,
                hwAcAmmeterTotalPowerFactorCH4
                    Integer32,
                hwAcAmmeterTotalActiveEngryAccCH4
                    Unsigned32,
                hwAcAmmeterChannel1DetectionObject
                    INTEGER,
                hwAcAmmeterChannel2DetectionObject
                    INTEGER,
                hwAcAmmeterChannel3DetectionObject
                    INTEGER,
                hwAcAmmeterChannel4DetectionObject
                    INTEGER,
                hwAcAmmeterAcOvervoltageThreshold
                    Unsigned32,
                hwAcAmmeterAcUndervoltageThreshold
                    Unsigned32,
                hwAcAmmeterAcSource
                    INTEGER,
                hwAcAmmeterPhaseL1ActivePowerCH1
                    Integer32,
                hwAcAmmeterPhaseL2ActivePowerCH1
                    Integer32,
                hwAcAmmeterPhaseL3ActivePowerCH1
                    Integer32,
                hwAcAmmeterPhaseL1ReactivePowerCH1
                    Integer32,
                hwAcAmmeterPhaseL2ReactivePowerCH1
                    Integer32,
                hwAcAmmeterPhaseL3ReactivePowerCH1
                    Integer32,
                hwAcAmmeterPhaseL1PowerFactorCH1
                    Integer32,
                hwAcAmmeterPhaseL2PowerFactorCH1
                    Integer32,
                hwAcAmmeterPhaseL3PowerFactorCH1
                    Integer32,
                hwAcAmmeterTotalReactivePowerCH1
                    Integer32,
                hwAcAmmeterOperStatus
                    INTEGER,
                hwAcAmmeterRowStatus
                    RowStatus
            }

        hwAcAmmeterIndex OBJECT-TYPE
            SYNTAX Unsigned32 (4096..20479)
            MAX-ACCESS read-only
            STATUS current
            DESCRIPTION
                "Ac Ammeter table index,which value range:4096 to 20479. Lines of the device list are restricted by the quantity of AcAmmeter"
            ::= { hwSiteAcAmmeterEntry 1 }

        hwAcAmmeterEquipId OBJECT-TYPE
            SYNTAX Unsigned32 (22001..22255)
            MAX-ACCESS read-only
            STATUS current
            DESCRIPTION
                "Ac Ammeter device ID. Value range: 022'001 to 022'255, in which the first digits indicate the device type and the last three digits indicate the device SN."
            ::= { hwSiteAcAmmeterEntry 2 }

        hwAcAmmeterEquipName OBJECT-TYPE
            SYNTAX OCTET STRING (SIZE (0..63))
            MAX-ACCESS read-only
            STATUS current
            DESCRIPTION
                "Ac Ammeter name, of the character string type, is used to specify Fans. Users can configure it.
                Otherwise, the configured character can not be any other languages except English."
            ::= { hwSiteAcAmmeterEntry 3 }

        hwAcAmmeterFrequency OBJECT-TYPE
            SYNTAX Unsigned32 (0..100000)
            MAX-ACCESS read-only
            STATUS current
            DESCRIPTION
                "Ac Ammeter frequency, 
                Value range: 0.00 to 1000.00.
                Unit: Hz.
                and the value is accurate to two decimal space (.01). 
                If the value is 2147483647(0x7FFFFFFF), it indicates that the value is invalid."
            ::= { hwSiteAcAmmeterEntry 4 }

        hwAcAmmeterPhaseL1Voltage OBJECT-TYPE
            SYNTAX Unsigned32 (0..200000)
            MAX-ACCESS read-only
            STATUS current
            DESCRIPTION
                "Ac Ammeter phase a voltage, 
                Value range: 0.00 to 2000.00.
                Unit: V.
                and the value is accurate to two decimal space (.01). 
                If the value is 2147483647(0x7FFFFFFF), it indicates that the value is invalid."
            ::= { hwSiteAcAmmeterEntry 5 }

        hwAcAmmeterPhaseL2Voltage OBJECT-TYPE
            SYNTAX Unsigned32 (0..200000)
            MAX-ACCESS read-only
            STATUS current
            DESCRIPTION
                "Ac Ammeter phase b voltage, 
                Value range: 0.00 to 2000.0.
                Unit: V.
                and the value is accurate to two decimal space (.01).
                If the value is 2147483647(0x7FFFFFFF), it indicates that the value is invalid."
            ::= { hwSiteAcAmmeterEntry 6 }

        hwAcAmmeterPhaseL3Voltage OBJECT-TYPE
            SYNTAX Unsigned32 (0..200000)
            MAX-ACCESS read-only
            STATUS current
            DESCRIPTION
                "Ac Ammeter phase c voltage, 
                Value range: 0.00 to 2000.0.
                Unit: V.
                and the value is accurate to two decimal space (.01). 
                If the value is 2147483647(0x7FFFFFFF), it indicates that the value is invalid."
            ::= { hwSiteAcAmmeterEntry 7 }

        hwAcAmmeterSetChannelNum OBJECT-TYPE
            SYNTAX Unsigned32 (1..4)
            MAX-ACCESS read-write
            STATUS current
            DESCRIPTION
                "Ac Ammeter set channel number, 
                Value range: 1 to 4. 
                Unit: NA.
                and the value is an integer (1).
                If the value is 2147483647(0x7FFFFFFF), it indicates that the value is invalid."
            ::= { hwSiteAcAmmeterEntry 8 }

        hwAcAmmeterClear OBJECT-TYPE
            SYNTAX INTEGER
                {
                clear(1)
                }
            MAX-ACCESS read-write
            STATUS current
            DESCRIPTION
                "Ac Ammeter clear communication failure . It is an enumeration type: 
                If the enumeration value is 1, it indicates that the ac ammeter clear communication failure alarm;"
            ::= { hwSiteAcAmmeterEntry 9 }

        hwAcAmmeterType OBJECT-TYPE
            SYNTAX Unsigned32 (0..65535)
            MAX-ACCESS read-only
            STATUS current
            DESCRIPTION
                "Ac Ammeter type, Value range: 0 to 65535. And the value is an integer(1)."
            ::= { hwSiteAcAmmeterEntry 10 }

        hwAcAmmeterVersion OBJECT-TYPE
            SYNTAX OCTET STRING (SIZE (0..56))
            MAX-ACCESS read-only
            STATUS current
            DESCRIPTION
                "Ac Ammeter version, of the character string type, is used to specify Ac Ammeter. Users can not configure it."
            ::= { hwSiteAcAmmeterEntry 11 }

        hwAcAmmeterPhaseL1CurrentCH1 OBJECT-TYPE
            SYNTAX Unsigned32 (0..100000)
            MAX-ACCESS read-only
            STATUS current
            DESCRIPTION
                "Ac Ammeter phase a current of channel 1, 
                Value range: 0.00 to 1000.0.
                Unit: A.
                and the value is accurate to two decimal space (.01). 
                If the value is 2147483647(0x7FFFFFFF), it indicates that the value is invalid."
            ::= { hwSiteAcAmmeterEntry 12 }

        hwAcAmmeterPhaseL2CurrentCH1 OBJECT-TYPE
            SYNTAX Unsigned32 (0..100000)
            MAX-ACCESS read-only
            STATUS current
            DESCRIPTION
                "Ac Ammeter phase b current of channel 1, 
                Value range: 0.00 to 1000.0.
                Unit: A.
                and the value is accurate to two decimal space (.01). 
                If the value is 2147483647(0x7FFFFFFF), it indicates that the value is invalid."
            ::= { hwSiteAcAmmeterEntry 13 }

        hwAcAmmeterPhaseL3CurrentCH1 OBJECT-TYPE
            SYNTAX Unsigned32 (0..100000)
            MAX-ACCESS read-only
            STATUS current
            DESCRIPTION
                "Ac Ammeter phase c current of channel 1, 
                Value range: 0.00 to 1000.0.
                Unit: A.
                and the value is accurate to two decimal space (.01).
                If the value is 2147483647(0x7FFFFFFF), it indicates that the value is invalid."
            ::= { hwSiteAcAmmeterEntry 14 }

        hwAcAmmeterTotalActivePowerCH1 OBJECT-TYPE
            SYNTAX Integer32 (-100000000..100000000)
            MAX-ACCESS read-only
            STATUS current
            DESCRIPTION
                "Ac Ammeter total active power of channel 1, 
                Value range: -1000000.00 to 1000000.00.
                Unit: kW.
                and the value is accurate to two decimal space (.01). 
                If the value is 2147483647(0x7FFFFFFF), it indicates that the value is invalid."
            ::= { hwSiteAcAmmeterEntry 15 }

        hwAcAmmeterTotalPowerFactorCH1 OBJECT-TYPE
            SYNTAX Integer32 ( -1000..1000)
            MAX-ACCESS read-only
            STATUS current
            DESCRIPTION
                "Ac Ammeter total power factor of channel 1, 
                Yada(0x800A) Value range: -10.00 to 10.00.  and the value is accurate to two decimal space (.01). 
                aim(0x900A) Value range: -1.00 to 1.00, and the value is accurate to two decimal space (.01). 
                iACmeter Rs485(0x81E3) Value range: 0.000 to 1.000, and the value is accurate to three decimal space (.001). 
                iACmeter(0x81AB) Value range: 0.000 to 1.000, and the value is accurate to three decimal space (.001). 
                If the value is 2147483647(0x7FFFFFFF), it indicates that the value is invalid."
            ::= { hwSiteAcAmmeterEntry 16 }

        hwAcAmmeterTotalActiveEngryAccCH1 OBJECT-TYPE
            SYNTAX Unsigned32 (0..100000000)
            MAX-ACCESS read-only
            STATUS current
            DESCRIPTION
                "Ac Ammeter total active engry acc of channel 1, 
                Value range: 0.00 to 1000000.00.
                Unit: kWh.
                and the value is accurate to two decimal space (.01). 
                If the value is 2147483647(0x7FFFFFFF), it indicates that the value is invalid."
            ::= { hwSiteAcAmmeterEntry 17 }

        hwAcAmmeterPhaseL1CurrentCH2 OBJECT-TYPE
            SYNTAX Unsigned32 (0..100000)
            MAX-ACCESS read-only
            STATUS current
            DESCRIPTION
                "Ac Ammeter phase a current of channel 2, 
                Value range: 0.00 to 1000.00.
                Unit: A.
                and the value is accurate to two decimal space (.01).
                If the value is 2147483647(0x7FFFFFFF), it indicates that the value is invalid."
            ::= { hwSiteAcAmmeterEntry 18 }

        hwAcAmmeterPhaseL2CurrentCH2 OBJECT-TYPE
            SYNTAX Unsigned32 (0..100000)
            MAX-ACCESS read-only
            STATUS current
            DESCRIPTION
                "Ac Ammeter phase b current of channel 2, 
                Value range: 0.00 to 1000.00.
                Unit: A.
                and the value is accurate to two decimal space (.01).
                If the value is 2147483647(0x7FFFFFFF), it indicates that the value is invalid."
            ::= { hwSiteAcAmmeterEntry 19 }

        hwAcAmmeterPhaseL3CurrentCH2 OBJECT-TYPE
            SYNTAX Unsigned32 (0..100000)
            MAX-ACCESS read-only
            STATUS current
            DESCRIPTION
                "Ac Ammeter phase c current of channel 2, 
                Value range: 0.00 to 1000.00.
                Unit: A.
                and the value is accurate to two decimal space (.01). 
                If the value is 2147483647(0x7FFFFFFF), it indicates that the value is invalid."
            ::= { hwSiteAcAmmeterEntry 20 }

        hwAcAmmeterTotalActivePowerCH2 OBJECT-TYPE
            SYNTAX Integer32 (-100000000..100000000)
            MAX-ACCESS read-only
            STATUS current
            DESCRIPTION
                "Ac Ammeter total active power of channel 2, 
                Value range: -1000000.00 to 1000000.00.
                Unit: kW.
                and the value is accurate to two decimal space (.01). 
                If the value is 2147483647(0x7FFFFFFF), it indicates that the value is invalid."
            ::= { hwSiteAcAmmeterEntry 21 }

        hwAcAmmeterTotalPowerFactorCH2 OBJECT-TYPE
            SYNTAX Integer32 ( -1000..1000)
            MAX-ACCESS read-only
            STATUS current
            DESCRIPTION
                "Ac Ammeter total power factor of channel 2, 
                Yada(0x800A) Value range: -10.00 to 10.00.  and the value is accurate to two decimal space (.01). 
                iACmeter Rs485(0x81E3) Value range: 0.000 to 1.000, and the value is accurate to three decimal space (.001). 
                iACmeter(0x81AB) Value range: 0.000 to 1.000, and the value is accurate to three decimal space (.001). 
                If the value is 2147483647(0x7FFFFFFF), it indicates that the value is invalid."
            ::= { hwSiteAcAmmeterEntry 22 }

        hwAcAmmeterTotalActiveEngryAccCH2 OBJECT-TYPE
            SYNTAX Unsigned32 (0..100000000)
            MAX-ACCESS read-only
            STATUS current
            DESCRIPTION
                "Ac Ammeter total active engry acc of channel 2, 
                Value range: 0.00 to 0..1000000.00.
                Unit: kWh.
                and the value is accurate to two decimal space (.01). 
                If the value is 2147483647(0x7FFFFFFF), it indicates that the value is invalid."
            ::= { hwSiteAcAmmeterEntry 23 }

        hwAcAmmeterPhaseL1CurrentCH3 OBJECT-TYPE
            SYNTAX Unsigned32 (0..100000)
            MAX-ACCESS read-only
            STATUS current
            DESCRIPTION
                "Ac Ammeter phase a current of channel 3, 
                Value range: 0.00 to 1000.00.
                Unit: A.
                and the value is accurate to two decimal space (.01). 
                If the value is 2147483647(0x7FFFFFFF), it indicates that the value is invalid."
            ::= { hwSiteAcAmmeterEntry 24 }

        hwAcAmmeterPhaseL2CurrentCH3 OBJECT-TYPE
            SYNTAX Unsigned32 (0..100000)
            MAX-ACCESS read-only
            STATUS current
            DESCRIPTION
                "Ac Ammeter phase b current of channel 3, 
                Value range: 0.00 to 1000.00.
                Unit: A.
                and the value is accurate to two decimal space (.01). 
                If the value is 2147483647(0x7FFFFFFF), it indicates that the value is invalid."
            ::= { hwSiteAcAmmeterEntry 25 }

        hwAcAmmeterPhaseL3CurrentCH3 OBJECT-TYPE
            SYNTAX Unsigned32 (0..100000)
            MAX-ACCESS read-only
            STATUS current
            DESCRIPTION
                "Ac Ammeter phase c current of channel 3, 
                Value range: 0.00 to 1000.00.
                Unit: A.
                and the value is accurate to two decimal space (.01). 
                If the value is 2147483647(0x7FFFFFFF), it indicates that the value is invalid."
            ::= { hwSiteAcAmmeterEntry 26 }

        hwAcAmmeterTotalActivePowerCH3 OBJECT-TYPE
            SYNTAX Integer32 (-100000000..100000000)
            MAX-ACCESS read-only
            STATUS current
            DESCRIPTION
                "Ac Ammeter total active power of channel 3, 
                Value range: -1000000.00 to 1000000.00.
                Unit: kW.
                and the value is accurate to two decimal space (.01). 
                If the value is 2147483647(0x7FFFFFFF), it indicates that the value is invalid."
            ::= { hwSiteAcAmmeterEntry 27 }

        hwAcAmmeterTotalPowerFactorCH3 OBJECT-TYPE
            SYNTAX Integer32 ( -1000..1000)
            MAX-ACCESS read-only
            STATUS current
            DESCRIPTION
                "Ac Ammeter total power factor of channel 3, 
                Yada(0x800A) Value range: -10.00 to 10.00.  and the value is accurate to two decimal space (.01). 
                iACmeter Rs485(0x81E3) Value range: 0.000 to 1.000, and the value is accurate to three decimal space (.001). 
                iACmeter(0x81AB) Value range: 0.000 to 1.000, and the value is accurate to three decimal space (.001). 
                If the value is 2147483647(0x7FFFFFFF), it indicates that the value is invalid."
            ::= { hwSiteAcAmmeterEntry 28 }

        hwAcAmmeterTotalActiveEngryAccCH3 OBJECT-TYPE
            SYNTAX Unsigned32 (0..100000000)
            MAX-ACCESS read-only
            STATUS current
            DESCRIPTION
                "Ac Ammeter total active engry acc of channel 3, 
                Value range: 0.00 to 0..1000000.00.
                Unit: kWh.
                and the value is accurate to two decimal space (.01). 
                If the value is 2147483647(0x7FFFFFFF), it indicates that the value is invalid."
            ::= { hwSiteAcAmmeterEntry 29 }

        hwAcAmmeterPhaseL1CurrentCH4 OBJECT-TYPE
            SYNTAX Unsigned32 (0..100000)
            MAX-ACCESS read-only
            STATUS current
            DESCRIPTION
                "Ac Ammeter phase a current of channel 4, 
                Value range: 0.00 to 1000.00.
                Unit: A.
                and the value is accurate to two decimal space (.01). 
                If the value is 2147483647(0x7FFFFFFF), it indicates that the value is invalid."
            ::= { hwSiteAcAmmeterEntry 30 }

        hwAcAmmeterPhaseL2CurrentCH4 OBJECT-TYPE
            SYNTAX Unsigned32 (0..100000)
            MAX-ACCESS read-only
            STATUS current
            DESCRIPTION
                "Ac Ammeter phase b current of channel 4, 
                Value range: 0.00 to 1000.00.
                Unit: A.
                and the value is accurate to two decimal space (.01). 
                If the value is 2147483647(0x7FFFFFFF), it indicates that the value is invalid."
            ::= { hwSiteAcAmmeterEntry 31 }

        hwAcAmmeterPhaseL3CurrentCH4 OBJECT-TYPE
            SYNTAX Unsigned32 (0..100000)
            MAX-ACCESS read-only
            STATUS current
            DESCRIPTION
                "Ac Ammeter phase c current of channel 4, 
                Value range: 0.00 to 1000.00.
                Unit: A.
                and the value is accurate to two decimal space (.01). 
                If the value is 2147483647(0x7FFFFFFF), it indicates that the value is invalid."
            ::= { hwSiteAcAmmeterEntry 32 }

        hwAcAmmeterTotalActivePowerCH4 OBJECT-TYPE
            SYNTAX Integer32 (-100000000..100000000)
            MAX-ACCESS read-only
            STATUS current
            DESCRIPTION
                "Ac Ammeter total active power of channel 4, 
                Value range: -1000000.00 to 1000000.00.
                Unit: kW.
                and the value is accurate to two decimal space (.01). 
                If the value is 2147483647(0x7FFFFFFF), it indicates that the value is invalid."
            ::= { hwSiteAcAmmeterEntry 33 }

        hwAcAmmeterTotalPowerFactorCH4 OBJECT-TYPE
            SYNTAX Integer32 ( -1000..1000)
            MAX-ACCESS read-only
            STATUS current
            DESCRIPTION
                "Ac Ammeter total power factor of channel 4, 
                Value range: -10.00 to 10.00.
                and the value is accurate to two decimal space (.01).
                If the value is 2147483647(0x7FFFFFFF), it indicates that the value is invalid."
            ::= { hwSiteAcAmmeterEntry 34 }

        hwAcAmmeterTotalActiveEngryAccCH4 OBJECT-TYPE
            SYNTAX Unsigned32 (0..100000000)
            MAX-ACCESS read-only
            STATUS current
            DESCRIPTION
                "Ac Ammeter total active engry acc of channel 4, 
                Value range: 0.00 to 1000000.00
                Unit: kWh.
                and the value is accurate to two decimal space (.01). 
                If the value is 2147483647(0x7FFFFFFF), it indicates that the value is invalid."
            ::= { hwSiteAcAmmeterEntry 35 }

        hwAcAmmeterChannel1DetectionObject OBJECT-TYPE
            SYNTAX INTEGER
                {
                none(1),
                acTotalInput(2),
                acMainEquipment(3),
                acTCEquipment(4),
                acOtherEquipment(5),
                unknown(255)
                }
            MAX-ACCESS read-write
            STATUS current
            DESCRIPTION
                "Detection object of the AC ammeter channel1. It is an enumeration type: 
                If the enumeration value is 1, it indicates that the object is none;
                If the enumeration value is 2, it indicates that the object is AC total input; 
                If the enumeration value is 3, it indicates that the object is AC main equipment;  
                If the enumeration value is 4, it indicates that the object is AC TC equipment;  
                If the enumeration value is 5, it indicates that the object is AC other equipment;  
                If the enumeration value is 255, it indicates that the object is unknown."
            ::= { hwSiteAcAmmeterEntry 36 }

        hwAcAmmeterChannel2DetectionObject OBJECT-TYPE
            SYNTAX INTEGER
                {
                none(1),
                acTotalInput(2),
                acMainEquipment(3),
                acTCEquipment(4),
                acOtherEquipment(5),
                unknown(255)
                }
            MAX-ACCESS read-write
            STATUS current
            DESCRIPTION
                "Detection object of the AC ammeter channel2. It is an enumeration type: 
                If the enumeration value is 1, it indicates that the object is none;
                If the enumeration value is 2, it indicates that the object is AC total input; 
                If the enumeration value is 4, it indicates that the object is AC main equipment;  
                If the enumeration value is 4, it indicates that the object is AC TC equipment;  
                If the enumeration value is 5, it indicates that the object is AC other equipment;  
                If the enumeration value is 255, it indicates that the object is unknown."
            ::= { hwSiteAcAmmeterEntry 37 }

        hwAcAmmeterChannel3DetectionObject OBJECT-TYPE
            SYNTAX INTEGER
                {
                none(1),
                acTotalInput(2),
                acMainEquipment(3),
                acTCEquipment(4),
                acOtherEquipment(5),
                unknown(255)
                }
            MAX-ACCESS read-write
            STATUS current
            DESCRIPTION
                "Detection object of the AC ammeter channel3. It is an enumeration type: 
                If the enumeration value is 1, it indicates that the object is none;
                If the enumeration value is 2, it indicates that the object is AC total input; 
                If the enumeration value is 3, it indicates that the object is AC main equipment;  
                If the enumeration value is 4, it indicates that the object is AC TC equipment;  
                If the enumeration value is 5, it indicates that the object is AC other equipment;  
                If the enumeration value is 255, it indicates that the object is unknown."
            ::= { hwSiteAcAmmeterEntry 38 }

        hwAcAmmeterChannel4DetectionObject OBJECT-TYPE
            SYNTAX INTEGER
                {
                none(1),
                acTotalInput(2),
                acMainEquipment(3),
                acTCEquipment(4),
                acOtherEquipment(5),
                unknown(255)
                }
            MAX-ACCESS read-write
            STATUS current
            DESCRIPTION
                "Detection object of the AC ammeter channel4. It is an enumeration type: 
                If the enumeration value is 1, it indicates that the object is none;
                If the enumeration value is 2, it indicates that the object is AC total input; 
                If the enumeration value is 3, it indicates that the object is AC main equipment;  
                If the enumeration value is 4, it indicates that the object is AC TC equipment;  
                If the enumeration value is 5, it indicates that the object is AC other equipment;  
                If the enumeration value is 255, it indicates that the object is unknown."
            ::= { hwSiteAcAmmeterEntry 39 }

        hwAcAmmeterAcOvervoltageThreshold OBJECT-TYPE
            SYNTAX Unsigned32 (60..300)
            MAX-ACCESS read-write
            STATUS current
            DESCRIPTION
                "Upper threshold of the AC voltage alarm, can be configued by users. 
                Value range: 60 to 300, 
                unit: V.  
                If the value is 2147483647(0x7FFFFFFF), it indicates that the value is invalid. 
                The default value is 280. "
            ::= { hwSiteAcAmmeterEntry 40 }

        hwAcAmmeterAcUndervoltageThreshold OBJECT-TYPE
            SYNTAX Unsigned32 (60..300)
            MAX-ACCESS read-write
            STATUS current
            DESCRIPTION
                "Lower threshold of the AC voltage alarm, can be configued by users. 
                Value range: 60 to 300, 
                unit: V.  
                If the value is 2147483647(0x7FFFFFFF), it indicates that the value is invalid. 
                The default value is 180. "
            ::= { hwSiteAcAmmeterEntry 41 }

        hwAcAmmeterAcSource OBJECT-TYPE
            SYNTAX INTEGER
                {
                other(1),
                mains(2),
                dg(3),
                mains2(4),
                dg2(5),
                unknown(255)
                }
            MAX-ACCESS read-write
            STATUS current
            DESCRIPTION
                "The AC source of the AC ammeter.It is an enumeration type: 
                If the enumeration value is 1, it indicates that the source is other;
                If the enumeration value is 2, it indicates that the source is mains; 
                If the enumeration value is 3, it indicates that the source is DG;
                If the equip is 5G customized ammeter and the enumeration value is 4, it indicates that the source is mains2; 
                If the equip is 5G custom ammeter and the enumeration value is 5, it indicates that the source is mains2; 
                If the enumeration value is 255, it indicates that the source is unknown.
                Only 5G customized ammeters allow users to get and set values 4 and 5."
            ::= { hwSiteAcAmmeterEntry 42 }

        hwAcAmmeterPhaseL1ActivePowerCH1 OBJECT-TYPE
            SYNTAX Integer32 (-100000000..100000000)
            MAX-ACCESS read-only
            STATUS current
            DESCRIPTION
                "The phase L1 Active Power of channel1; 
                Value range: -1000000.00 to 1000000.00, 
                and the value is accurate to two decimal place (.01).
                unit: kW."
            ::= { hwSiteAcAmmeterEntry 43 }

        hwAcAmmeterPhaseL2ActivePowerCH1 OBJECT-TYPE
            SYNTAX Integer32 (-100000000..100000000)
            MAX-ACCESS read-only
            STATUS current
            DESCRIPTION
                "The phase L2 Active Power of channel1; 
                Value range: -1000000.00 to 1000000.00, 
                and the value is accurate to two decimal place (.01).
                unit: kW"
            ::= { hwSiteAcAmmeterEntry 44 }

        hwAcAmmeterPhaseL3ActivePowerCH1 OBJECT-TYPE
            SYNTAX Integer32 (-100000000..100000000)
            MAX-ACCESS read-only
            STATUS current
            DESCRIPTION
                "The phase L3 Active Power of channel1; 
                Value range: -1000000.00 to 1000000.00, 
                and the value is accurate to two decimal place (.01).
                unit: kW."
            ::= { hwSiteAcAmmeterEntry 45 }

        hwAcAmmeterPhaseL1ReactivePowerCH1 OBJECT-TYPE
            SYNTAX Integer32 (-100000000..100000000)
            MAX-ACCESS read-only
            STATUS current
            DESCRIPTION
                "The phase L1 Reactive Power of channel1; 
                Value range: -1000000.00 to 1000000.00, 
                and the value is accurate to two decimal place (.01).
                unit: kvar."
            ::= { hwSiteAcAmmeterEntry 46 }

        hwAcAmmeterPhaseL2ReactivePowerCH1 OBJECT-TYPE
            SYNTAX Integer32 (-100000000..100000000)
            MAX-ACCESS read-only
            STATUS current
            DESCRIPTION
                "The phase L2 Reactive Power of channel1; 
                Value range: -1000000.00 to 1000000.00, 
                and the value is accurate to two decimal place (.01).
                unit: kvar."
            ::= { hwSiteAcAmmeterEntry 47 }

        hwAcAmmeterPhaseL3ReactivePowerCH1 OBJECT-TYPE
            SYNTAX Integer32 (-100000000..100000000)
            MAX-ACCESS read-only
            STATUS current
            DESCRIPTION
                "The phase L3 Active Power of channel1; 
                Value range: -1000000.00 to 1000000.00, 
                and the value is accurate to two decimal place (.01).
                unit: kvar."
            ::= { hwSiteAcAmmeterEntry 48 }

        hwAcAmmeterPhaseL1PowerFactorCH1 OBJECT-TYPE
            SYNTAX Integer32 (-100..100)
            MAX-ACCESS read-only
            STATUS current
            DESCRIPTION
                "The phase L1 Power Factor of channel1; 
                Value range: -1.00 to 1.00, 
                and the value is accurate to three decimal place (.01).
                unit: NA."
            ::= { hwSiteAcAmmeterEntry 49 }

        hwAcAmmeterPhaseL2PowerFactorCH1 OBJECT-TYPE
            SYNTAX Integer32 (-100..100)
            MAX-ACCESS read-only
            STATUS current
            DESCRIPTION
                "The phase L2 Power Factor of channel1; 
                Value range: -1.00 to 1.00, 
                and the value is accurate to two decimal place (.01).
                unit: NA."
            ::= { hwSiteAcAmmeterEntry 50 }

        hwAcAmmeterPhaseL3PowerFactorCH1 OBJECT-TYPE
            SYNTAX Integer32 (-100..100)
            MAX-ACCESS read-only
            STATUS current
            DESCRIPTION
                "The phase L3 Power Factor of channel1; 
                Value range: -1.00 to 1.00, 
                and the value is accurate to two decimal place (.01).
                unit: NA."
            ::= { hwSiteAcAmmeterEntry 51 }

        hwAcAmmeterTotalReactivePowerCH1 OBJECT-TYPE
            SYNTAX Integer32 (-100000000..100000000)
            MAX-ACCESS read-only
            STATUS current
            DESCRIPTION
                "The Total Reactive Power of channel1; 
                Value range: -1000000.00 to 1000000.00, 
                and the value is accurate to two decimal place (.01).
                unit: kvar."
            ::= { hwSiteAcAmmeterEntry 52 }

        hwAcAmmeterOperStatus OBJECT-TYPE
            SYNTAX INTEGER
                {
                normal(1),
                fault(2),
                unknown(255)
                }
            MAX-ACCESS read-only
            STATUS current
            DESCRIPTION
                "State of the Ac Ammeter. It is an enumeration type: 
                If the enumeration value is 1, it indicates that the Ac Ammeter is in the normal state;
                If the enumeration value is 2, it indicates that the Ac Ammeter is in the fault state;  
                If the enumeration value is 255, it indicates that the Ac Ammeter is in the unknown state;  "
            ::= { hwSiteAcAmmeterEntry 99 }

        hwAcAmmeterRowStatus OBJECT-TYPE
            SYNTAX RowStatus
            MAX-ACCESS read-create
            STATUS current
            DESCRIPTION
                "RowStatus fo Ac Ammeter table."
            ::= { hwSiteAcAmmeterEntry 100 }

        hwSiteDG OBJECT IDENTIFIER ::= { hwSiteMonitorMIBObjects 12 }

        hwDGGroup OBJECT IDENTIFIER ::= { hwSiteDG 1 }

        hwDGGroupId OBJECT-TYPE
            SYNTAX Unsigned32
            MAX-ACCESS read-only
            STATUS current
            DESCRIPTION
                "Device group ID of the DG module. It is the unique ID of the DG module group, and its default value: 023,000. 
                The first digits indicate the device type and the last three digits indicate the device SN. 
                If the last three digits are 000, it indicates a virtual device. "
            ::= { hwDGGroup 1 }

        hwDGGroupName OBJECT-TYPE
            SYNTAX OCTET STRING (SIZE (0..56))
            MAX-ACCESS read-only
            STATUS current
            DESCRIPTION
                "Name of the DG module group, character string type, is used to specify the DG module group. Otherwise, the configured character can not be any other languages except English."
            ::= { hwDGGroup 2 }

        hwDGAmount OBJECT-TYPE
            SYNTAX Unsigned32 (0..2)
            MAX-ACCESS read-write
            STATUS current
            DESCRIPTION
                "Total quantity of the DG modules. Value range: 0 to 2. unit:pcs."
            ::= { hwDGGroup 3 }

        hwDGMovableAutoEn OBJECT-TYPE
            SYNTAX INTEGER
                {
                disable(1),
                enable(2),
                unknown(255)
                }
            MAX-ACCESS read-write
            STATUS current
            DESCRIPTION
                "Mobile DG auto enable"
            ::= { hwDGGroup 7 }

        hwDGMobileDGChrgBatt OBJECT-TYPE
            SYNTAX INTEGER
                {
                disable(1),
                enable(2),
                unknown(255)
                }
            MAX-ACCESS read-write
            STATUS current
            DESCRIPTION
                "Mobile DG enable charging battery"
            ::= { hwDGGroup 8 }

        hwDGMainsRatedFreq OBJECT-TYPE
            SYNTAX Unsigned32 (400..700)
            MAX-ACCESS read-write
            STATUS current
            DESCRIPTION
                "Set DG output AC frequency"
            ::= { hwDGGroup 9 }

        hwDGMobileFrqDelta OBJECT-TYPE
            SYNTAX Unsigned32 (1..50)
            MAX-ACCESS read-write
            STATUS current
            DESCRIPTION
                "Set AC frequency variable range, can be configured by users. 
                Value range: 0.1 to 5, 
                unit: Hz, 
                and the value is accurate to one decimal place (.1)."
            ::= { hwDGGroup 10 }

        hwDGGroupSetTable OBJECT-TYPE
            SYNTAX SEQUENCE OF HwDGGroupSetEntry
            MAX-ACCESS not-accessible
             STATUS current
             DESCRIPTION
                "/"
            ::= { hwDGGroup 11 }

        hwDGGroupSetEntry OBJECT-TYPE
                        SYNTAX HwDGGroupSetEntry
            MAX-ACCESS not-accessible
             STATUS current
             DESCRIPTION
                "/"
            INDEX { hwDGGroupTimedStopDGEnable }
            ::= { hwDGGroupSetTable 1 }

        HwDGGroupSetEntry            ::= SEQUENCE {
                hwDGGroupTimedStopDGEnable
                    INTEGER,
                hwDGGroupRunTimeBeforeStopDG
                    Unsigned32,
                hwDGGroupSoftStartTime
                    Unsigned32,
                hwDGGroupDodStartDG
                    Unsigned32,
                hwDGGroupMinChgTime
                    Unsigned32,
                hwDGGroupMaxChgTime
                    Unsigned32,
                hwDGGroupTimedStopDGTime
                    OCTET STRING
            }

        hwDGGroupTimedStopDGEnable OBJECT-TYPE
            SYNTAX INTEGER
                {
                disable(1),
                enable(2),
                unknown(255)
                }
            MAX-ACCESS read-write
            STATUS current
            DESCRIPTION
                "Scheduled DG shutdown enable.Value range: Disable is 0, Enable is 1."
            ::= { hwDGGroupSetEntry 1 }

        hwDGGroupRunTimeBeforeStopDG OBJECT-TYPE
            SYNTAX Unsigned32 (0..720)
            MAX-ACCESS read-write
            STATUS current
            DESCRIPTION
                "On duration before timing shutdown.Value range: 0 to 720, unit: min."
            ::= { hwDGGroupSetEntry 2 }

        hwDGGroupSoftStartTime OBJECT-TYPE
            SYNTAX Unsigned32 (1..5)
            MAX-ACCESS read-write
            STATUS current
            DESCRIPTION
                "Soft start time.Value range: 1 to 5, unit: min."
            ::= { hwDGGroupSetEntry 3 }

        hwDGGroupDodStartDG OBJECT-TYPE
            SYNTAX Unsigned32 (5..90)
            MAX-ACCESS read-write
            STATUS current
            DESCRIPTION
                "DOD starts the DG.Value range: 5 to 90, unit: %."
            ::= { hwDGGroupSetEntry 4 }

        hwDGGroupMinChgTime OBJECT-TYPE
            SYNTAX Unsigned32 (0..2880)
            MAX-ACCESS read-write
            STATUS current
            DESCRIPTION
                "Minimum charging time.Value range: 0 to 2880, unit: min."
            ::= { hwDGGroupSetEntry 5 }

        hwDGGroupMaxChgTime OBJECT-TYPE
            SYNTAX Unsigned32 (60..2880)
            MAX-ACCESS read-write
            STATUS current
            DESCRIPTION
                "Maximum charging time.Value range: 60 to 2880, unit: min."
            ::= { hwDGGroupSetEntry 6 }

        hwDGGroupTimedStopDGTime OBJECT-TYPE
            SYNTAX OCTET STRING (SIZE (0..60))
            MAX-ACCESS read-write
            STATUS current
            DESCRIPTION
                "Scheduled DG shutdown time.Value range: 0 to 60, unit: HH:MM:SS."
            ::= { hwDGGroupSetEntry 7 }

        hwDG OBJECT IDENTIFIER ::= { hwSiteDG 2 }

        hwDGTable OBJECT-TYPE
            SYNTAX SEQUENCE OF HwDGEntry
            MAX-ACCESS not-accessible
             STATUS current
             DESCRIPTION
                "/"
            ::= { hwDG 1 }

        hwDGEntry OBJECT-TYPE
                        SYNTAX HwDGEntry
            MAX-ACCESS not-accessible
             STATUS current
             DESCRIPTION
                "/"
            INDEX { hwDGIndex }
            ::= { hwDGTable 1 }

        HwDGEntry            ::= SEQUENCE {
                hwDGIndex
                    Integer32,
                hwDGEquipId
                    Unsigned32,
                hwDGEquipName
                    OCTET STRING,
                hwDGType
                    INTEGER,
                hwDGAphaseVoltage
                    Unsigned32,
                hwDGBphaseVoltage
                    Unsigned32,
                hwDGCphaseVoltage
                    Unsigned32,
                hwDGAphaseCurrent
                    Unsigned32,
                hwDGBphaseCurrent
                    Unsigned32,
                hwDGCphaseCurrent
                    Unsigned32,
                hwDGOutputPower
                    Unsigned32,
                hwDGFrequency
                    Unsigned32,
                hwDGBatteryVoltage
                    Unsigned32,
                hwDGTotalRuntime
                    Unsigned32,
                hwDGAphasePowerFactor
                    Integer32,
                hwDGBphasePowerFactor
                    Integer32,
                hwDGCphasePowerFactor
                    Integer32,
                hwDGLoadRate
                    Unsigned32,
                hwDGOnOffControl
                    INTEGER,
                hwDGFaultReset
                    INTEGER,
                hwDGMaintenanceConfirm
                    INTEGER,
                hwDGRatePower
                    Unsigned32,
                hwDGMaxPowerRatio
                    Unsigned32,
                hwDGOperStatus
                    INTEGER,
                hwDGRowStatus
                    RowStatus
            }

        hwDGIndex OBJECT-TYPE
            SYNTAX Integer32 (1..256)
            MAX-ACCESS read-only
            STATUS current
            DESCRIPTION
                "DG table index,which value range:1 to 256. Lines of the device list are restricted by the quantity of DG."
            ::= { hwDGEntry 1 }

        hwDGEquipId OBJECT-TYPE
            SYNTAX Unsigned32 (23001..23255)
            MAX-ACCESS read-only
            STATUS current
            DESCRIPTION
                "DG device ID. Value range: 023'001 to 023'255, in which the first digits indicate the device type and the last three digits indicate the device SN."
            ::= { hwDGEntry 2 }

        hwDGEquipName OBJECT-TYPE
            SYNTAX OCTET STRING (SIZE (0..63))
            MAX-ACCESS read-only
            STATUS current
            DESCRIPTION
                "Device name of the DG module, character string type, is used to specify the DG module. Otherwise, the configured character can not be any other languages except English."
            ::= { hwDGEntry 3 }

        hwDGType OBJECT-TYPE
            SYNTAX INTEGER
                {
                intelligent(1),
                non_intelligent(2),
                unknown(255)
                }
            MAX-ACCESS read-only
            STATUS current
            DESCRIPTION
                "Specific type of the DG module. It is an enumeration type:
                  If the enumeration value is 1, it indicates a intelligent DG module; 
                  If the enumeration value is 2, it indicates a non_intelligent module; 
                  If the enumeration value is 255, it indicates a unknown module; 
                Note: This MIB node has been specially processed using the RegisterDifferSignalHandleType() method, and the node values and signal values have a non enumeration mapping relationship."
            ::= { hwDGEntry 4 }

        hwDGAphaseVoltage OBJECT-TYPE
            SYNTAX Unsigned32 (0..8000)
            MAX-ACCESS read-only
            STATUS current
            DESCRIPTION
                "A-phase voltage. 
                Value range: 0.0 to 800.0, 
                unit: V, 
                and the value is accurate to one decimal place (.1)."
            ::= { hwDGEntry 5 }

        hwDGBphaseVoltage OBJECT-TYPE
            SYNTAX Unsigned32 (0..8000)
            MAX-ACCESS read-only
            STATUS current
            DESCRIPTION
                "B-phase voltage. 
                Value range: 0.0 to 800.0, 
                unit: V, 
                and the value is accurate to one decimal place (.1)."
            ::= { hwDGEntry 6 }

        hwDGCphaseVoltage OBJECT-TYPE
            SYNTAX Unsigned32 (0..8000)
            MAX-ACCESS read-only
            STATUS current
            DESCRIPTION
                "C-phase voltage. 
                Value range: 0.0 to 800.0, 
                unit: V, 
                and the value is accurate to one decimal place (.1)."
            ::= { hwDGEntry 7 }

        hwDGAphaseCurrent OBJECT-TYPE
            SYNTAX Unsigned32 (0..5000)
            MAX-ACCESS read-only
            STATUS current
            DESCRIPTION
                "A-phase current. 
                Value range: 0.0 to 500.0, 
                unit: A, 
                and the value is accurate to one decimal place (.1)."
            ::= { hwDGEntry 8 }

        hwDGBphaseCurrent OBJECT-TYPE
            SYNTAX Unsigned32 (0..5000)
            MAX-ACCESS read-only
            STATUS current
            DESCRIPTION
                "B-phase current. 
                Value range: 0.0 to 500.0, 
                unit: A, 
                and the value is accurate to one decimal place (.1)."
            ::= { hwDGEntry 9 }

        hwDGCphaseCurrent OBJECT-TYPE
            SYNTAX Unsigned32 (0..5000)
            MAX-ACCESS read-only
            STATUS current
            DESCRIPTION
                "C-phase current. 
                Value range: 0.0 to 500.0, 
                unit: A, 
                and the value is accurate to one decimal place (.1)."
            ::= { hwDGEntry 10 }

        hwDGOutputPower OBJECT-TYPE
            SYNTAX Unsigned32 (0..48000)
            MAX-ACCESS read-only
            STATUS current
            DESCRIPTION
                "DG output power.
                Value range: 0.00 to 480.00, 
                unit: kW, 
                and the value is two decimal space (.01)."
            ::= { hwDGEntry 11 }

        hwDGFrequency OBJECT-TYPE
            SYNTAX Unsigned32 (0..1200)
            MAX-ACCESS read-only
            STATUS current
            DESCRIPTION
                "The frequency of DG. 
                Value range: 0.0 to 120.0, 
                unit: Hz, 
                and the value is one decimal space (.1)."
            ::= { hwDGEntry 12 }

        hwDGBatteryVoltage OBJECT-TYPE
            SYNTAX Unsigned32 (0..600)
            MAX-ACCESS read-only
            STATUS current
            DESCRIPTION
                "The voltage of DG battery. 
                Value range: 0.0 to 60.0, 
                unit: V, 
                and the value is one decimal space (.1)."
            ::= { hwDGEntry 13 }

        hwDGTotalRuntime OBJECT-TYPE
            SYNTAX Unsigned32 (0..8760000)
            MAX-ACCESS read-only
            STATUS current
            DESCRIPTION
                "The total running time of DG, 
                Value range: 0.0 to 876000.0,
                unit: h, 
                and the value is one decimal space (.1)."
            ::= { hwDGEntry 14 }

        hwDGAphasePowerFactor OBJECT-TYPE
            SYNTAX Integer32 (-100..100)
            MAX-ACCESS read-only
            STATUS current
            DESCRIPTION
                "A phase power factor of DG, 
                Value range: -1.00 to 1.00, 
                unit: , 
                and the value is two decimal space (.01)."
            ::= { hwDGEntry 15 }

        hwDGBphasePowerFactor OBJECT-TYPE
            SYNTAX Integer32 (-100..100)
            MAX-ACCESS read-only
            STATUS current
            DESCRIPTION
                "B phase power factor of DG, 
                Value range: -1.00 to 1.00,
                unit: , 
                and the value is two decimal space (.01)."
            ::= { hwDGEntry 16 }

        hwDGCphasePowerFactor OBJECT-TYPE
            SYNTAX Integer32 (-100..100)
            MAX-ACCESS read-only
            STATUS current
            DESCRIPTION
                "C phase power factor of DG, 
                Value range: -1.00 to 1.00, 
                unit: , 
                and the value is two decimal space (.01)."
            ::= { hwDGEntry 17 }

        hwDGLoadRate OBJECT-TYPE
            SYNTAX Unsigned32 (0..2000)
            MAX-ACCESS read-only
            STATUS current
            DESCRIPTION
                "The load rate of DG, 
                Value range: 0.0 to 200.0, 
                unit: %, 
                and the value is one decimal space (.1). "
            ::= { hwDGEntry 18 }

        hwDGOnOffControl OBJECT-TYPE
            SYNTAX INTEGER
                {
                on(1),
                off(2),
                unknown(255)
                }
            MAX-ACCESS read-write
            STATUS current
            DESCRIPTION
                "Power-on or power-off of the DG module, is an enumeration value. Users can modify the enumeration value of this node, thus controlling of the power-on or power-off of the DG module:
                  If the NMS notifies the SNMP agent that this node is set to 1, it indicates power-on of the DG module;
                  If the NMS notifies the SNMP agent that this node is set to 2, it indicates power-off of the DG module.
                  If the NMS notifies the SNMP agent that this node is set to 255, it indicates unknown of the DG module."
            ::= { hwDGEntry 19 }

        hwDGFaultReset OBJECT-TYPE
            SYNTAX INTEGER
                {
                reset(1),
                unknown(255)
                }
            MAX-ACCESS read-write
            STATUS current
            DESCRIPTION
                "DG fault reset."
            ::= { hwDGEntry 20 }

        hwDGMaintenanceConfirm OBJECT-TYPE
            SYNTAX INTEGER
                {
                reset(1),
                unknown(255)
                }
            MAX-ACCESS read-write
            STATUS current
            DESCRIPTION
                "DG maintenance confirm."
            ::= { hwDGEntry 21 }

        hwDGRatePower OBJECT-TYPE
            SYNTAX Unsigned32 (1..50000)
            MAX-ACCESS read-write
            STATUS current
            DESCRIPTION
                "DG rated power.Value range: 1 to 5000, unit: kW."
            ::= { hwDGEntry 24 }

        hwDGMaxPowerRatio OBJECT-TYPE
            SYNTAX Unsigned32 (0..1000)
            MAX-ACCESS read-write
            STATUS current
            DESCRIPTION
                "DG maximum output power ratio.Value range: 0 to 100, unit: %."
            ::= { hwDGEntry 25 }

        hwDGOperStatus OBJECT-TYPE
            SYNTAX INTEGER
                {
                stop(1),
                running(2),
                unknown(255)
                }
            MAX-ACCESS read-only
            STATUS current
            DESCRIPTION
                "State of the DG. It is an enumeration type: 
                If the enumeration value is 1, it indicates that the DG is in the stop state;
                If the enumeration value is 2, it indicates that the DG is in the running state; 
                If the enumeration value is 255, it indicates that the DG is in the unknown state;  "
            ::= { hwDGEntry 99 }

        hwDGRowStatus OBJECT-TYPE
            SYNTAX RowStatus
            MAX-ACCESS read-create
            STATUS current
            DESCRIPTION
                "RowStatus fo DG."
            ::= { hwDGEntry 100 }

        hwSiteSSU OBJECT IDENTIFIER ::= { hwSiteMonitorMIBObjects 13 }

        hwSSUGroup OBJECT IDENTIFIER ::= { hwSiteSSU 1 }

        hwSSUGroupId OBJECT-TYPE
            SYNTAX Unsigned32
            MAX-ACCESS read-only
            STATUS current
            DESCRIPTION
                "Device group ID of the SSU module. It is the unique ID of the SSU module group, and its default value: 024,000. 
                The first digits indicate the device type and the last three digits indicate the device SN. If the last three digits are 000, it indicates a virtual device. "
            ::= { hwSSUGroup 1 }

        hwSSUGroupName OBJECT-TYPE
            SYNTAX OCTET STRING (SIZE (0..56))
            MAX-ACCESS read-only
            STATUS current
            DESCRIPTION
                "Name of the SSU module group, character string type, is used to specify the SSU module group. 
                Otherwise, the configured character can not be any other languages except English."
            ::= { hwSSUGroup 2 }

        hwSSUTotalCurrent OBJECT-TYPE
            SYNTAX Unsigned32 (0..240000)
            MAX-ACCESS read-only
            STATUS current
            DESCRIPTION
                "The total output current of SSU. 
                Value range: 0.0 to 24000.0, 
                unit: A, 
                and the value is one decimal space (.1)."
            ::= { hwSSUGroup 3 }

        hwSSUTotalOutputPowerConsumption OBJECT-TYPE
            SYNTAX Unsigned32 (0..1000000000)
            MAX-ACCESS read-only
            STATUS current
            DESCRIPTION
                "The total output current of SSU. 
                Value range: 0.0 to 10000000.0, 
                unit: kWh, 
                and the value is one decimal space (.1)."
            ::= { hwSSUGroup 4 }

        hwSSUClearLostAlarms OBJECT-TYPE
            SYNTAX INTEGER
                {
                normal(1), 
                clear(2),
                unknown(255)
                }
            MAX-ACCESS read-write
            STATUS current
            DESCRIPTION
                "Clear the lost alarm of SSU."
            ::= { hwSSUGroup 5 }

        hwSSUAmount OBJECT-TYPE
            SYNTAX Unsigned32 (0..240)
            MAX-ACCESS read-only
            STATUS current
            DESCRIPTION
                "Total quantity of the SSU modules. Value range: 0 to 240. unit:pcs."
            ::= { hwSSUGroup 6 }

        hwSSUTotalOutputPower OBJECT-TYPE
            SYNTAX Unsigned32 (0..100000000)
            MAX-ACCESS read-only
            STATUS current
            DESCRIPTION
                "resolution: 0.1kw"
            ::= { hwSSUGroup 7 }

        hwSSUFaultNumber OBJECT-TYPE
            SYNTAX Unsigned32 (0..240)
            MAX-ACCESS read-only
            STATUS current
            DESCRIPTION
                "number of fault solar modules "
            ::= { hwSSUGroup 8 }

        hwSSUGroupCurrentHourlyOutputPower OBJECT-TYPE
            SYNTAX Unsigned32 (0..4294967295)
            MAX-ACCESS read-only
            STATUS current
            DESCRIPTION
                "The SSU group current hourly output power; 
                Value range: 0 to 4294967295, 
                and the value is accurate to two decimal place (.01)."
            ::= { hwSSUGroup 9 }

        hwSSUGroupCurrentDayOutputPower OBJECT-TYPE
            SYNTAX Unsigned32 (0..4294967295)
            MAX-ACCESS read-only
            STATUS current
            DESCRIPTION
                "The SSU group current-day output power; 
                Value range: 0 to 4294967295, 
                and the value is accurate to two decimal place (.01)."
            ::= { hwSSUGroup 10 }

        hwSSUGroupCurrentWeeklyOutputPower OBJECT-TYPE
            SYNTAX Unsigned32 (0..4294967295)
            MAX-ACCESS read-only
            STATUS current
            DESCRIPTION
                "The SSU group current weekly output power; 
                Value range: 0 to 4294967295, 
                and the value is accurate to two decimal place (.01)."
            ::= { hwSSUGroup 11 }

        hwSSUGroupCurrentMonthlyOutputPower OBJECT-TYPE
            SYNTAX Unsigned32 (0..4294967295)
            MAX-ACCESS read-only
            STATUS current
            DESCRIPTION
                "The SSU group current monthly output power; 
                Value range: 0 to 4294967295, 
                and the value is accurate to two decimal place (.01)."
            ::= { hwSSUGroup 12 }

        hwSSUGroupCurrentYearlyOutputPower OBJECT-TYPE
            SYNTAX Unsigned32 (0..4294967295)
            MAX-ACCESS read-only
            STATUS current
            DESCRIPTION
                "The SSU group current yearly output power; 
                Value range: 0 to 4294967295, 
                and the value is accurate to two decimal place (.01)."
            ::= { hwSSUGroup 13 }

        hwSSU OBJECT IDENTIFIER ::= { hwSiteSSU 2 }

        hwSSUTable OBJECT-TYPE
            SYNTAX SEQUENCE OF HwSSUEntry
            MAX-ACCESS not-accessible
             STATUS current
             DESCRIPTION
                "/"
            ::= { hwSSU 1 }

        hwSSUEntry OBJECT-TYPE
                        SYNTAX HwSSUEntry
            MAX-ACCESS not-accessible
             STATUS current
             DESCRIPTION
                "/"
            INDEX { hwSSUIndex }
            ::= { hwSSUTable 1 }

        HwSSUEntry            ::= SEQUENCE {
                hwSSUIndex
                    Integer32,
                hwSSUEquipId
                    Unsigned32,
                hwSSUEquipName
                    OCTET STRING,
                hwSSURunningState
                    INTEGER,
                hwSSUInputVoltage
                    Unsigned32,
                hwSSUOutputVoltage
                    Unsigned32,
                hwSSUOutputCurrent
                    Unsigned32,
                hwSSUAddress
                    Unsigned32,
                hwSSUFatherEquipName
                    OCTET STRING,
                hwSSURowStatus
                    RowStatus,
                hwSSUPowerOnOffStatus
                    INTEGER,
                hwSSUSoftwareVersion
                    OCTET STRING,
                hwSSUHardwareVersion
                    OCTET STRING,
                hwSSUBarcode
                    OCTET STRING,
                hwSSUOutputPower
                    Unsigned32,
                hwSSUPCUSoftwareVersion
                    OCTET STRING,
                hwSSUCCOSoftwareVersion
                    OCTET STRING,
                hwSSUInputPower
                    Unsigned32,
                hwSSUInputCurrent
                    Unsigned32
            }

        hwSSUIndex OBJECT-TYPE
            SYNTAX Integer32 (0..256)
            MAX-ACCESS read-only
            STATUS current
            DESCRIPTION
                "SSU table index,which value range:1 to 256. Lines of the device list are restricted by the quantity of SSU."
            ::= { hwSSUEntry 1 }

        hwSSUEquipId OBJECT-TYPE
            SYNTAX Unsigned32 (24001..24255)
            MAX-ACCESS read-only
            STATUS current
            DESCRIPTION
                "SSU device ID. Value range: 024'001 to 024'255, in which the first digits indicate the device type and the last three digits indicate the device SN."
            ::= { hwSSUEntry 2 }

        hwSSUEquipName OBJECT-TYPE
            SYNTAX OCTET STRING (SIZE (0..63))
            MAX-ACCESS read-only
            STATUS current
            DESCRIPTION
                "Device name of the SSU module, character string type, is used to specify the SSU module. 
                Otherwise, the configured character can not be any other languages except English."
            ::= { hwSSUEntry 3 }

        hwSSURunningState OBJECT-TYPE
            SYNTAX INTEGER
                {
                on(1),
                off(2),
                nullOper(255)
                }
            MAX-ACCESS read-only
            STATUS current
            DESCRIPTION
                "The running status of the SSU module. It is an enumeration type: 
                  If the enumeration value is 1, it indicates that the SSU module is power on ;
                  If the enumeration value is 2, it indicates that the SSU module is power off;
                 If the enumeration value is 255, it indicates that the SSU module is nulloper;   "
            ::= { hwSSUEntry 4 }

        hwSSUInputVoltage OBJECT-TYPE
            SYNTAX Unsigned32 (0..5000)
            MAX-ACCESS read-only
            STATUS current
            DESCRIPTION
                "The input voltage of SSU, 
                Value range: 0.0 to 500.0, 
                unit: V, 
                and the value is one decimal space (.1)."
            ::= { hwSSUEntry 5 }

        hwSSUOutputVoltage OBJECT-TYPE
            SYNTAX Unsigned32 (0..30000)
            MAX-ACCESS read-only
            STATUS current
            DESCRIPTION
                "The output voltage of SSU, 
                Value range: 0.0 to 3000.0, 
                unit: V, 
                and the value is one decimal space (.1)."
            ::= { hwSSUEntry 6 }

        hwSSUOutputCurrent OBJECT-TYPE
            SYNTAX Unsigned32 (0..10000)
            MAX-ACCESS read-only
            STATUS current
            DESCRIPTION
                "The output current of SSU, 
                Value range: 0.0 to 1000.0, 
                unit: A, 
                and the value is one decimal space (.1)."
            ::= { hwSSUEntry 7 }

        hwSSUAddress OBJECT-TYPE
            SYNTAX Unsigned32 (0..100   )
            MAX-ACCESS read-only
            STATUS current
            DESCRIPTION
                "The address of SSU, 
                Value range: 0 to 100, 
                unit: , 
                and the value is  an integer (1)."
            ::= { hwSSUEntry 8 }

        hwSSUFatherEquipName OBJECT-TYPE
            SYNTAX OCTET STRING (SIZE (0..63))
            MAX-ACCESS read-only
            STATUS current
            DESCRIPTION
                "Father device name of the SSU module. "
            ::= { hwSSUEntry 9 }

        hwSSURowStatus OBJECT-TYPE
            SYNTAX RowStatus
            MAX-ACCESS read-create
            STATUS current
            DESCRIPTION
                "RowStatus fo SSU."
            ::= { hwSSUEntry 100 }

        hwSSUPowerOnOffStatus OBJECT-TYPE
            SYNTAX INTEGER
                {
                powerOn(1), powerOff(2) 
                }
            MAX-ACCESS read-only
            STATUS current
            DESCRIPTION
                "On/Off Status of SSU, It is an enumeration type: 
                  If the enumeration value is 1, it indicates that the powerOn;
                  If the enumeration value is 2, it indicates that the powerOff."
            ::= { hwSSUEntry 10 }

        hwSSUSoftwareVersion OBJECT-TYPE
            SYNTAX OCTET STRING
            MAX-ACCESS read-only
            STATUS current
            DESCRIPTION
                "Software Version of SSU, of the character string type. Signal value length is 5."
            ::= { hwSSUEntry 11 }

        hwSSUHardwareVersion OBJECT-TYPE
            SYNTAX OCTET STRING
            MAX-ACCESS read-only
            STATUS current
            DESCRIPTION
                "Hardware Version of SSU, of the character string type. Signal value length is 5."
            ::= { hwSSUEntry 12 }

        hwSSUBarcode OBJECT-TYPE
            SYNTAX OCTET STRING
            MAX-ACCESS read-only
            STATUS current
            DESCRIPTION
                "Barcode of SSU, of the character string type. Signal value length is 5."
            ::= { hwSSUEntry 13 }

        hwSSUOutputPower OBJECT-TYPE
            SYNTAX Unsigned32 (0..10000000)
            MAX-ACCESS read-only
            STATUS current
            DESCRIPTION
                "Output Power of SSU, 
                Value range: 0 to 100000, 
                unit: kW, 
                and the value is two decimal space (.01)."
            ::= { hwSSUEntry 14 }

        hwSSUPCUSoftwareVersion OBJECT-TYPE
            SYNTAX OCTET STRING
            MAX-ACCESS read-only
            STATUS current
            DESCRIPTION
                "PCU Software Version, of the character string type. Signal value length is 30, Only exists on the solar module (two in one module)."
            ::= { hwSSUEntry 15 }

        hwSSUCCOSoftwareVersion OBJECT-TYPE
            SYNTAX OCTET STRING
            MAX-ACCESS read-only
            STATUS current
            DESCRIPTION
                "CCO Software Version, of the character string type. Signal value length is 30, Only exists on the solar module (two in one module)."
            ::= { hwSSUEntry 16 }

        hwSSUInputPower OBJECT-TYPE
            SYNTAX Unsigned32 (0..1000000)
            MAX-ACCESS read-only
            STATUS current
            DESCRIPTION
                "Input Power of SSU, 
                Value range: 0.0 to 100000.0, 
                units: kW, 
                and the value is one decimal space (.1)."
            ::= { hwSSUEntry 17 }

        hwSSUInputCurrent OBJECT-TYPE
            SYNTAX Unsigned32 (0..10000)
            MAX-ACCESS read-only
            STATUS current
            DESCRIPTION
                "The input current of SSU, 
                Value range: 0.0 to 1000.0, 
                units: A, 
                and the value is one decimal space (.1)."
            ::= { hwSSUEntry 18 }

        hwSiteBatteryCabinets OBJECT IDENTIFIER ::= { hwSiteMonitorMIBObjects 14 }

        hwSiteBatteryCabinetEquip OBJECT IDENTIFIER ::= { hwSiteBatteryCabinets 2 }

        hwSiteBatteryCabinetTable OBJECT-TYPE
            SYNTAX SEQUENCE OF HwSiteBatteryCabinetEntry
            MAX-ACCESS not-accessible
             STATUS current
             DESCRIPTION
                "/"
            ::= { hwSiteBatteryCabinetEquip 1 }

        hwSiteBatteryCabinetEntry OBJECT-TYPE
                        SYNTAX HwSiteBatteryCabinetEntry
            MAX-ACCESS not-accessible
             STATUS current
             DESCRIPTION
                "/"
            INDEX { hwBatteryCabinetIndex }
            ::= { hwSiteBatteryCabinetTable 1 }

        HwSiteBatteryCabinetEntry            ::= SEQUENCE {
                hwBatteryCabinetIndex
                    Unsigned32,
                hwBatteryCabinetEquipId
                    Unsigned32,
                hwBatteryCabinetEquipName
                    OCTET STRING,
                hwBatteryCabinetIndoorVentTemp
                    Integer32,
                hwBatteryCabinetBattTemp
                    Integer32,
                hwBatteryCabinetFan1Speed
                    Integer32,
                hwBatteryCabinetFan2Speed
                    Integer32,
                hwBatteryCabinetFan3Speed
                    Integer32,
                hwBatteryCabinetFan4Speed
                    Integer32,
                hwBatteryCabinetAirConditionerStatus
                    INTEGER,
                hwBatteryCabinetCompressorStatus
                    INTEGER,
                hwBatteryCabinetInternalFanSpeed
                    Integer32,
                hwBatteryCabinetExternalFanSpeed
                    Integer32,
                hwBatteryCabinetAirConditionerRuntime
                    Unsigned32,
                hwBatteryCabinetCompressorRuntime
                    Unsigned32,
                hwBatteryCabinetAirConWorkTemp
                    Integer32,
                hwBatteryCabinetAirConStopTemp
                    Integer32,
                hwBatteryCabinetCommStatus
                    INTEGER,
                hwBatteryCabinetRowStatus
                    RowStatus
            }

        hwBatteryCabinetIndex OBJECT-TYPE
            SYNTAX Unsigned32 (4096..20479)
            MAX-ACCESS read-only
            STATUS current
            DESCRIPTION
                "Battery Cabinet table index,which value is according to the actual subject. Lines of the device list are restricted by the quantity of Battery Cabinet"
            ::= { hwSiteBatteryCabinetEntry 1 }

        hwBatteryCabinetEquipId OBJECT-TYPE
            SYNTAX Unsigned32 (25000..25255)
            MAX-ACCESS read-only
            STATUS current
            DESCRIPTION
                "Battery Cabinet device ID. Value range: 025'001 to 025'255, in which the first digits indicate the device type and the last three digits indicate the device SN."
            ::= { hwSiteBatteryCabinetEntry 2 }

        hwBatteryCabinetEquipName OBJECT-TYPE
            SYNTAX OCTET STRING (SIZE (0..63))
            MAX-ACCESS read-only
            STATUS current
            DESCRIPTION
                "Battery Cabinet name, of the character string type, is used to specify battery cabinet. Users can configure it.
                Otherwise, the configured character can not be any other languages except English.
                "
            ::= { hwSiteBatteryCabinetEntry 3 }

        hwBatteryCabinetIndoorVentTemp OBJECT-TYPE
            SYNTAX Integer32 ( -40..100)
            MAX-ACCESS read-only
            STATUS current
            DESCRIPTION
                "Indoor vent temperature. It is an environment parameter collected in real time. 
                Value range: -40 to +100, 
                unit: centigrade, 
                and the value is an integer (1).  
                If the value is -99999, it indicates that the temperature sensor is not configured."
            ::= { hwSiteBatteryCabinetEntry 4 }

        hwBatteryCabinetBattTemp OBJECT-TYPE
            SYNTAX Integer32 ( -40..100)
            MAX-ACCESS read-only
            STATUS current
            DESCRIPTION
                "Battery temperature. It is an environment parameter collected in real time.
                Value range: -40 to +100, 
                unit: centigrade, 
                and the value is an integer (1).  
                If the value is -99999, it indicates that the temperature sensor is not configured."
            ::= { hwSiteBatteryCabinetEntry 5 }

        hwBatteryCabinetFan1Speed OBJECT-TYPE
            SYNTAX Integer32 (0..10000)
            MAX-ACCESS read-only
            STATUS current
            DESCRIPTION
                "Fan 1 speed, 
                Value range: 0.0 to 10000.0.
                Unit: rpm,
                the value is an integer (1). 
                If the value is -1, it indicates that the fan is not configured."
            ::= { hwSiteBatteryCabinetEntry 6 }

        hwBatteryCabinetFan2Speed OBJECT-TYPE
            SYNTAX Integer32 (0..10000)
            MAX-ACCESS read-only
            STATUS current
            DESCRIPTION
                "Fan 2 speed, 
                Value range: 0.0 to 10000.0.
                Unit: rpm,
                the value is an integer (1). 
                If the value is -1, it indicates that the fan is not configured."
            ::= { hwSiteBatteryCabinetEntry 7 }

        hwBatteryCabinetFan3Speed OBJECT-TYPE
            SYNTAX Integer32 (0..10000)
            MAX-ACCESS read-only
            STATUS current
            DESCRIPTION
                "Fan 3 speed, 
                Value range: 0.0 to 10000.0.
                Unit: rpm,
                the value is an integer (1). 
                If the value is -1, it indicates that the fan is not configured."
            ::= { hwSiteBatteryCabinetEntry 8 }

        hwBatteryCabinetFan4Speed OBJECT-TYPE
            SYNTAX Integer32 (0..10000)
            MAX-ACCESS read-only
            STATUS current
            DESCRIPTION
                "Fan 4 speed, 
                Value range: 0.0 to 10000.0.
                Unit: rpm,
                the value is an integer (1). 
                If the value is -1, it indicates that the fan is not configured."
            ::= { hwSiteBatteryCabinetEntry 9 }

        hwBatteryCabinetAirConditionerStatus OBJECT-TYPE
            SYNTAX INTEGER
                {
                standby(1),
                run(2),
                fault(3),
                unknown(255)
                }
            MAX-ACCESS read-only
            STATUS current
            DESCRIPTION
                "State of the airconditioner. It is an enumeration type: 
                If the enumeration value is 1, it indicates that the airconditioner is in the standby state;
                If the enumeration value is 2, it indicates that the airconditioner is in the run state;  
                If the enumeration value is 3, it indicates that the airconditioner is in the fault state;  
                If the enumeration value is 255, it indicates airconditioner status unknown. "
            ::= { hwSiteBatteryCabinetEntry 10 }

        hwBatteryCabinetCompressorStatus OBJECT-TYPE
            SYNTAX INTEGER
                {
                standby(1),
                run(2),
                fault(3),
                unknown(255)
                }
            MAX-ACCESS read-only
            STATUS current
            DESCRIPTION
                "State of the compressor. It is an enumeration type: 
                If the enumeration value is 1, it indicates that the compressor is in the standby state;
                If the enumeration value is 2, it indicates that the compressor is in the run state;  
                If the enumeration value is 3, it indicates that the compressor is in the fault state;  
                If the enumeration value is 255, it indicates compressor operation status unknown. "
            ::= { hwSiteBatteryCabinetEntry 11 }

        hwBatteryCabinetInternalFanSpeed OBJECT-TYPE
            SYNTAX Integer32 (0..10000)
            MAX-ACCESS read-only
            STATUS current
            DESCRIPTION
                "Internal Fan speed,
                Value range: 0 to 10000.
                Unit: rpm,
                the value is an integer (1). 
                If the value is -1, it indicates that the fan is not configured."
            ::= { hwSiteBatteryCabinetEntry 12 }

        hwBatteryCabinetExternalFanSpeed OBJECT-TYPE
            SYNTAX Integer32 (0..10000)
            MAX-ACCESS read-only
            STATUS current
            DESCRIPTION
                "External Fan speed, 
                Value range: 0 to 10000.
                Unit: rpm,
                the value is an integer (1). 
                If the value is -1, it indicates that the temperature sensor is not configured."
            ::= { hwSiteBatteryCabinetEntry 13 }

        hwBatteryCabinetAirConditionerRuntime OBJECT-TYPE
            SYNTAX Unsigned32
            MAX-ACCESS read-only
            STATUS current
            DESCRIPTION
                "Total runtime of the air conditioner. 
                Value unit: hour (h), 
                and the value is an integer (1). 
                If the value is 2147483647(0x7FFFFFFF), it indicates that the value is invalid."
            ::= { hwSiteBatteryCabinetEntry 14 }

        hwBatteryCabinetCompressorRuntime OBJECT-TYPE
            SYNTAX Unsigned32
            MAX-ACCESS read-only
            STATUS current
            DESCRIPTION
                "Total runtime of the compressor. 
                Value unit: hour (h), 
                and the value is an integer (1). 
                If the value is 2147483647(0x7FFFFFFF), it indicates that the value is invalid."
            ::= { hwSiteBatteryCabinetEntry 15 }

        hwBatteryCabinetAirConWorkTemp OBJECT-TYPE
            SYNTAX Integer32 ( -20..80)
            MAX-ACCESS read-write
            STATUS current
            DESCRIPTION
                "Battery cabinet aircondition power on temperature point, 
                Value range:-20 to 80 
                Unit: degC.
                and the value is an integer (1)."
            ::= { hwSiteBatteryCabinetEntry 16 }

        hwBatteryCabinetAirConStopTemp OBJECT-TYPE
            SYNTAX Integer32 ( -20..80)
            MAX-ACCESS read-write
            STATUS current
            DESCRIPTION
                "Battery cabinet aircondition power off temperature point, 
                Value range:-20 to 80 
                Unit: degC.
                and the value is an integer(1)."
            ::= { hwSiteBatteryCabinetEntry 17 }

        hwBatteryCabinetCommStatus OBJECT-TYPE
            SYNTAX INTEGER
                {
                normal(1),
                failed(2),
                unknown(255)
                }
            MAX-ACCESS read-only
            STATUS current
            DESCRIPTION
                "Communication state of the Battery Cabinet. It is an enumeration type: 
                If the enumeration value is 1, it indicates normal communication;
                If the enumeration value is 2, it indicates a communication failure;
                If the enumeration value is 255, it indicates that the Inverter is in the unknown state;  "
            ::= { hwSiteBatteryCabinetEntry 99 }

        hwBatteryCabinetRowStatus OBJECT-TYPE
            SYNTAX RowStatus
            MAX-ACCESS read-create
            STATUS current
            DESCRIPTION
                "RowStatus fo Battery Cabinet table."
            ::= { hwSiteBatteryCabinetEntry 100 }

        hwSiteEsdu OBJECT IDENTIFIER ::= { hwSiteMonitorMIBObjects 15 }

        hwEsduTable OBJECT-TYPE
            SYNTAX SEQUENCE OF HwEsduEntry
            MAX-ACCESS not-accessible
             STATUS current
             DESCRIPTION
                "/"
            ::= { hwSiteEsdu 2 }

        hwEsduEntry OBJECT-TYPE
                        SYNTAX HwEsduEntry
            MAX-ACCESS not-accessible
             STATUS current
             DESCRIPTION
                "/"
            INDEX { hwEsduIndex }
            ::= { hwEsduTable 1 }

        HwEsduEntry            ::= SEQUENCE {
                hwEsduIndex
                    Unsigned32,
                hwEsduEquipId
                    Unsigned32,
                hwEsduEquipName
                    OCTET STRING,
                hwEsduSetDigitalInput1AlarmCondition
                    INTEGER,
                hwEsduDigitalInput1OperStatus
                    INTEGER,
                hwEsduSetDigitalInput2AlarmCondition
                    INTEGER,
                hwEsduDigitalInput2OperStatus
                    INTEGER,
                hwEsduSetDigitalInput3AlarmCondition
                    INTEGER,
                hwEsduDigitalInput3OperStatus
                    INTEGER,
                hwEsduSetDigitalInput4AlarmCondition
                    INTEGER,
                hwEsduDigitalInput4OperStatus
                    INTEGER,
                hwEsduSetDigitalInput5AlarmCondition
                    INTEGER,
                hwEsduDigitalInput5OperStatus
                    INTEGER,
                hwEsduSetDigitalInput6AlarmCondition
                    INTEGER,
                hwEsduDigitalInput6OperStatus
                    INTEGER,
                hwEsduSetDigitalInput7AlarmCondition
                    INTEGER,
                hwEsduDigitalInput7OperStatus
                    INTEGER,
                hwEsduSetDigitalInput8AlarmCondition
                    INTEGER,
                hwEsduDigitalInput8OperStatus
                    INTEGER,
                hwEsduSetDigitalInput9AlarmCondition
                    INTEGER,
                hwEsduDigitalInput9OperStatus
                    INTEGER,
                hwEsduSetDigitalInput10AlarmCondition
                    INTEGER,
                hwEsduDigitalInput10OperStatus
                    INTEGER,
                hwEsduSetDigitalInput11AlarmCondition
                    INTEGER,
                hwEsduDigitalInput11OperStatus
                    INTEGER,
                hwEsduSetDigitalInput12AlarmCondition
                    INTEGER,
                hwEsduDigitalInput12OperStatus
                    INTEGER,
                hwEsduBtempValue
                    Integer32,
                hwEsduBtempOperStatus
                    INTEGER,
                hwEsduTemp1Value
                    Integer32,
                hwEsduTemp1HighLimit
                    Integer32,
                hwEsduTemp1LowLimit
                    Integer32,
                hwEsduTemp1OperStatus
                    INTEGER,
                hwEsduTemp2Value
                    Integer32,
                hwEsduTemp2HighLimit
                    Integer32,
                hwEsduTemp2LowLimit
                    Integer32,
                hwEsduTemp2OperStatus
                    INTEGER,
                hwEsduDoorSensorConnect
                    INTEGER
            }

        hwEsduIndex OBJECT-TYPE
            SYNTAX Unsigned32 (3428..3443)
            MAX-ACCESS read-only
            STATUS current
            DESCRIPTION
                "ESDU equip index,which value is according to the actual subject. Lines of the device list are restricted by the quantity of Battery Cabinet"
            ::= { hwEsduEntry 1 }

        hwEsduEquipId OBJECT-TYPE
            SYNTAX Unsigned32 (28001..28255)
            MAX-ACCESS read-only
            STATUS current
            DESCRIPTION
                "Esdu device ID. Value range: 028,001 to 028,255, in which the first digits indicate the device type and the last three digits indicate the device SN."
            ::= { hwEsduEntry 2 }

        hwEsduEquipName OBJECT-TYPE
            SYNTAX OCTET STRING (SIZE (0..63))
            MAX-ACCESS read-only
            STATUS current
            DESCRIPTION
                "/"
            ::= { hwEsduEntry 3 }

        hwEsduSetDigitalInput1AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 4 }

        hwEsduDigitalInput1OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 5 }

        hwEsduSetDigitalInput2AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 6 }

        hwEsduDigitalInput2OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 7 }

        hwEsduSetDigitalInput3AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 8 }

        hwEsduDigitalInput3OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 9 }

        hwEsduSetDigitalInput4AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 10 }

        hwEsduDigitalInput4OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 11 }

        hwEsduSetDigitalInput5AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 12 }

        hwEsduDigitalInput5OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 13 }

        hwEsduSetDigitalInput6AlarmCondition OBJECT-TYPE
            SYNTAX INTEGER
                {
                close(1),
                open(2),
                unknown(255)
                }
            MAX-ACCESS read-write
            STATUS current
            DESCRIPTION
                "Spare digital alarm state. It is an enumeration value.If the value of the node is 1, it indicates a high-tension alarm;If the value of the node is 2, it indicates a low-tension alarm;If the value of the node is 255, it indicates airconditioner status unknown."
            ::= { hwEsduEntry 14 }

        hwEsduDigitalInput6OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 15 }

        hwEsduSetDigitalInput7AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 16 }

        hwEsduDigitalInput7OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 17 }

        hwEsduSetDigitalInput8AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 18 }

        hwEsduDigitalInput8OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 19 }

        hwEsduSetDigitalInput9AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 20 }

        hwEsduDigitalInput9OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 21 }

        hwEsduSetDigitalInput10AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 22 }

        hwEsduDigitalInput10OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 23 }

        hwEsduSetDigitalInput11AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 24 }

        hwEsduDigitalInput11OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 25 }

        hwEsduSetDigitalInput12AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 26 }

        hwEsduDigitalInput12OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 27 }

        hwEsduBtempValue OBJECT-TYPE
            SYNTAX Integer32 ( -40..80)
            MAX-ACCESS read-only
            STATUS current
            DESCRIPTION
                "Temp1. It is an environment parameter collected in real time. 
                Value range: -40 to +80, 
                Unit: degC
                and the value is an integer (1).  
                If the value is -1024, it indicates that the temperature sensor is not configured."
            ::= { hwEsduEntry 28 }

        hwEsduBtempOperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwEsduEntry 31 }

        hwEsduTemp1Value OBJECT-TYPE
            SYNTAX Integer32 ( -40..80)
            MAX-ACCESS read-only
            STATUS current
            DESCRIPTION
                "Temp1. It is an environment parameter collected in real time. 
                Value range: -40 to +80, 
                unit: centigrade (degC), 
                and the value is an integer (1).  
                If the value is -1024, it indicates that the temperature sensor is not configured."
            ::= { hwEsduEntry 32 }

        hwEsduTemp1HighLimit OBJECT-TYPE
            SYNTAX Integer32 (25..80)
            MAX-ACCESS read-write
            STATUS current
            DESCRIPTION
                "Upper threshold of the temp1 alarm, can be configured by users. 
                Value range: 25 to 80, 
                unit: centigrade (degC), 
                and the value is an integer (1).  
                If the value is 2147483647(0x7FFFFFFF), it indicates that the value is invalid."
            ::= { hwEsduEntry 33 }

        hwEsduTemp1LowLimit OBJECT-TYPE
            SYNTAX Integer32 ( -20..20)
            MAX-ACCESS read-write
            STATUS current
            DESCRIPTION
                "Lower threshold of the temp1 alarm, can be configured by users. 
                Value range: -20 to 20, 
                unit: centigrade (degC), 
                and the value is an integer (1).  
                If the value is 2147483647(0x7FFFFFFF), it indicates that the value is invalid."
            ::= { hwEsduEntry 34 }

        hwEsduTemp1OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwEsduEntry 35 }

        hwEsduTemp2Value OBJECT-TYPE
            SYNTAX Integer32 ( -40..80)
            MAX-ACCESS read-only
            STATUS current
            DESCRIPTION
                "Temp2. It is an environment parameter collected in real time. 
                Value range: -40 to +80, 
                unit: centigrade (degC), 
                and the value is an integer (1).  
                If the value is -1024, it indicates that the temperature sensor is not configured."
            ::= { hwEsduEntry 36 }

        hwEsduTemp2HighLimit OBJECT-TYPE
            SYNTAX Integer32 (25..80)
            MAX-ACCESS read-write
            STATUS current
            DESCRIPTION
                "Upper threshold of the temp2 alarm, can be configured by users. 
                Value range: 25 to 80, 
                unit: centigrade (degC), 
                and the value is an integer (1).  
                If the value is 2147483647(0x7FFFFFFF), it indicates that the value is invalid."
            ::= { hwEsduEntry 37 }

        hwEsduTemp2LowLimit OBJECT-TYPE
            SYNTAX Integer32 ( -20..20)
            MAX-ACCESS read-write
            STATUS current
            DESCRIPTION
                "Lower threshold of the temp2 alarm, can be configured by users. 
                Value range: -20 to 20,
                 unit: centigrade (degC), 
                and the value is an integer (1).  
                If the value is 2147483647(0x7FFFFFFF), it indicates that the value is invalid."
            ::= { hwEsduEntry 38 }

        hwEsduTemp2OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp2 sensor. It is an enumeration type: 
                  If the enumeration value is 1, it indicates that the site temp2 sensor is in the normal state; 
                  If the enumeration value is 2, it indicates that the temp2 sensor is over temperature; 
                  If the enumeration value is 3, it indicates that the temp2 sensor is under temperature; 
                  If the enumeration value is 4, it indicates that the temp2 sensor is not in slot;
                  If the enumeration value is 5, it indicates that the temp2 sensor is fault;
                  If the enumeration value is 254, it indicates that temp2 alarm resume; 
                  If the enumeration value is 255, it indicates temp2 sensor operation status unknown."
            ::= { hwEsduEntry 39 }

        hwEsduDoorSensorConnect OBJECT-TYPE
            SYNTAX INTEGER
                {
                disable(1),enable(2),unknown(255)
                }
            MAX-ACCESS read-write
            STATUS current
            DESCRIPTION
                "Door Sensor Connected; It is an enumeration value, and can be configured. 
                If the enumeration value is 1, it indicates Door Sensor is disable;
                If the enumeration value is 2, it indicates Door Sensor is enalble;
                If the enumeration value is 255, it indicates timed boost charge is unknown. "
            ::= { hwEsduEntry 40 }

        hwSiteIbox OBJECT IDENTIFIER ::= { hwSiteMonitorMIBObjects 20 }

        hwSiteIboxTable OBJECT-TYPE
            SYNTAX SEQUENCE OF HwSiteIboxEntry
            MAX-ACCESS not-accessible
             STATUS current
             DESCRIPTION
                "/"
            ::= { hwSiteIbox 1 }

        hwSiteIboxEntry OBJECT-TYPE
                        SYNTAX HwSiteIboxEntry
            MAX-ACCESS not-accessible
             STATUS current
             DESCRIPTION
                "/"
            INDEX { hwIboxIndex }
            ::= { hwSiteIboxTable 1 }

        HwSiteIboxEntry            ::= SEQUENCE {
                hwIboxIndex
                    Unsigned32,
                hwIboxEquipId
                    Unsigned32,
                hwIboxEquipName
                    OCTET STRING,
                hwIbatEquipNum
                    Unsigned32
            }

        hwIboxIndex OBJECT-TYPE
            SYNTAX Unsigned32 (560..575)
            MAX-ACCESS read-only
            STATUS current
            DESCRIPTION
                "ibox table index,which value is according to the actual subject. Lines of the device list are restricted by the quantity of ibox"
            ::= { hwSiteIboxEntry 1 }

        hwIboxEquipId OBJECT-TYPE
            SYNTAX Unsigned32 (29001..29255)
            MAX-ACCESS read-only
            STATUS current
            DESCRIPTION
                "ibox device ID. Value range: 029'001 to 029'255, in which the first digits indicate the device type and the last three digits indicate the device SN."
            ::= { hwSiteIboxEntry 2 }

        hwIboxEquipName OBJECT-TYPE
            SYNTAX OCTET STRING (SIZE (0..63))
            MAX-ACCESS read-only
            STATUS current
            DESCRIPTION
                "Ibox name, of the character string type, is used to specify battery cabinet. Users can configure it.
                Otherwise, the configured character can not be any other languages except English.
                "
            ::= { hwSiteIboxEntry 3 }

        hwIbatEquipNum OBJECT-TYPE
            SYNTAX Unsigned32 (0..96)
            MAX-ACCESS read-write
            STATUS current
            DESCRIPTION
                "Number of Batteries.
                Value range: 0 to 96,
                and the value is an integer (1).
                If the value is 2147483647(0x7FFFFFFF), it indicates that the value is invalid.
                 
                "
            ::= { hwSiteIboxEntry 4 }

        hwSiteIbat OBJECT IDENTIFIER ::= { hwSiteMonitorMIBObjects 21 }

        hwSiteIbatTable OBJECT-TYPE
            SYNTAX SEQUENCE OF HwSiteIbatEntry
            MAX-ACCESS not-accessible
             STATUS current
             DESCRIPTION
                "/"
            ::= { hwSiteIbat 1 }

        hwSiteIbatEntry OBJECT-TYPE
                        SYNTAX HwSiteIbatEntry
            MAX-ACCESS not-accessible
             STATUS current
             DESCRIPTION
                "/"
            INDEX { hwIbatIndex }
            ::= { hwSiteIbatTable 1 }

        HwSiteIbatEntry            ::= SEQUENCE {
                hwIbatIndex
                    Unsigned32,
                hwIbatEquipId
                    Unsigned32,
                hwIbatEquipName
                    OCTET STRING,
                hwIbatTemperature
                    Integer32,
                hwIbatVoltage
                    Unsigned32,
                hwIbatResistance
                    Unsigned32
            }

        hwIbatIndex OBJECT-TYPE
            SYNTAX Unsigned32 (24576..26112)
            MAX-ACCESS read-only
            STATUS current
            DESCRIPTION
                "ibox table index,which value is according to the actual subject. Lines of the device list are restricted by the quantity of ibox"
            ::= { hwSiteIbatEntry 1 }

        hwIbatEquipId OBJECT-TYPE
            SYNTAX Unsigned32 (30001..31537)
            MAX-ACCESS read-only
            STATUS current
            DESCRIPTION
                "ibat device ID. Value range: 030'001 to 031'537, in which the first digits indicate the device type and the last three digits indicate the device SN."
            ::= { hwSiteIbatEntry 2 }

        hwIbatEquipName OBJECT-TYPE
            SYNTAX OCTET STRING (SIZE (0..63))
            MAX-ACCESS read-only
            STATUS current
            DESCRIPTION
                "Ibat name, of the character string type, is used to specify battery cabinet. Users can configure it.
                Otherwise, the configured character can not be any other languages except English.
                "
            ::= { hwSiteIbatEntry 3 }

        hwIbatTemperature OBJECT-TYPE
            SYNTAX Integer32 (-50..125)
            MAX-ACCESS read-only
            STATUS current
            DESCRIPTION
                "Ibat temperature. It is a ibat  parameter collected in real time. 
                Value range: -50 to +125, 
                unit: centigrade (degC), 
                and the value is an integer (1).
                If the value is 2147483647(0x7FFFFFFF), it indicates that ibox temperature sensor is not configured.
                "
            ::= { hwSiteIbatEntry 4 }

        hwIbatVoltage OBJECT-TYPE
            SYNTAX Unsigned32 (0..1000)
            MAX-ACCESS read-only
            STATUS current
            DESCRIPTION
                "Ibat Voltage of the ibat. It is an inherent attribute. 
                Value range: 0.0 to 100.0, 
                unit: V, 
                and the value is accurate to one decimal place (.1).  
                If the value is 2147483647(0x7FFFFFFF), it indicates that the value is invalid.  
                "
            ::= { hwSiteIbatEntry 5 }

        hwIbatResistance OBJECT-TYPE
            SYNTAX Unsigned32 (0..100000000)
            MAX-ACCESS read-only
            STATUS current
            DESCRIPTION
                "IbatResistance
                Value range: 0 to 1000000, 
                unit:  (mohm), 
                and the value is accurate to two decimal place (.01). 
                "
            ::= { hwSiteIbatEntry 6 }

        hwSiteCommExBoard OBJECT IDENTIFIER ::= { hwSiteMonitorMIBObjects 22 }

        hwSiteCommExBoardTable OBJECT-TYPE
            SYNTAX SEQUENCE OF HwSiteCommExBoardEntry
            MAX-ACCESS not-accessible
             STATUS current
             DESCRIPTION
                "/"
            ::= { hwSiteCommExBoard 1 }

        hwSiteCommExBoardEntry OBJECT-TYPE
                        SYNTAX HwSiteCommExBoardEntry
            MAX-ACCESS not-accessible
             STATUS current
             DESCRIPTION
                "/"
            INDEX { hwCommExBoardIndex }
            ::= { hwSiteCommExBoardTable 1 }

        HwSiteCommExBoardEntry            ::= SEQUENCE {
                hwCommExBoardIndex
                    Unsigned32,
                hwCommExBoardEquipId
                    Unsigned32,
                hwCommExBoardEquipName
                    OCTET STRING
            }

        hwCommExBoardIndex OBJECT-TYPE
            SYNTAX Unsigned32 (1297..1301)
            MAX-ACCESS read-only
            STATUS current
            DESCRIPTION
                "Communication Expansion Board table index,which value is according to the actual subject. Lines of the device list are restricted by the quantity of Communication Expansion Board"
            ::= { hwSiteCommExBoardEntry 1 }

        hwCommExBoardEquipId OBJECT-TYPE
            SYNTAX Unsigned32 (32266..33049)
            MAX-ACCESS read-only
            STATUS current
            DESCRIPTION
                "Communication Expansion Board device ID. Value range: 032,256 to 033,249, in which the first digits indicate the device type and the last three digits indicate the device SN."
            ::= { hwSiteCommExBoardEntry 2 }

        hwCommExBoardEquipName OBJECT-TYPE
            SYNTAX OCTET STRING (SIZE (0..63))
            MAX-ACCESS read-only
            STATUS current
            DESCRIPTION
                "Communication Expansion Board name, of the character string type, is used to specify battery cabinet. Users can configure it.
                Otherwise, the configured character can not be any other languages except English.
                "
            ::= { hwSiteCommExBoardEntry 3 }

        hwSiteDGCommExBoard OBJECT IDENTIFIER ::= { hwSiteMonitorMIBObjects 23 }

        hwSiteDGCommExBoardTable OBJECT-TYPE
            SYNTAX SEQUENCE OF HwSiteDGCommExBoardEntry
            MAX-ACCESS not-accessible
             STATUS current
             DESCRIPTION
                "/"
            ::= { hwSiteDGCommExBoard 1 }

        hwSiteDGCommExBoardEntry OBJECT-TYPE
                        SYNTAX HwSiteDGCommExBoardEntry
            MAX-ACCESS not-accessible
             STATUS current
             DESCRIPTION
                "/"
            INDEX { hwDGCommExBoardIndex }
            ::= { hwSiteDGCommExBoardTable 1 }

        HwSiteDGCommExBoardEntry            ::= SEQUENCE {
                hwDGCommExBoardIndex
                    Unsigned32,
                hwDGCommExBoardEquipId
                    Unsigned32,
                hwDGCommExBoardEquipName
                    OCTET STRING
            }

        hwDGCommExBoardIndex OBJECT-TYPE
            SYNTAX Unsigned32 (2185)
            MAX-ACCESS read-only
            STATUS current
            DESCRIPTION
                "DG Communication Expansion Board table index,which value is according to the actual subject. Lines of the device list are restricted by the quantity of DG Communication Expansion Board"
            ::= { hwSiteDGCommExBoardEntry 1 }

        hwDGCommExBoardEquipId OBJECT-TYPE
            SYNTAX Unsigned32 (34001)
            MAX-ACCESS read-only
            STATUS current
            DESCRIPTION
                "DG Communication Expansion Board device ID. Value range: 034'001, in which the first digits indicate the device type and the last three digits indicate the device SN."
            ::= { hwSiteDGCommExBoardEntry 2 }

        hwDGCommExBoardEquipName OBJECT-TYPE
            SYNTAX OCTET STRING (SIZE (0..63))
            MAX-ACCESS read-only
            STATUS current
            DESCRIPTION
                "DG Communication Expansion Board name, of the character string type, is used to specify battery cabinet. Users can configure it.
                Otherwise, the configured character can not be any other languages except English.
                "
            ::= { hwSiteDGCommExBoardEntry 3 }

        hwAcbGroupEquip OBJECT IDENTIFIER ::= { hwSiteMonitorMIBObjects 17 }

        hwAcbGroupSampTable OBJECT-TYPE
            SYNTAX SEQUENCE OF HwAcbGroupSampEntry
            MAX-ACCESS not-accessible
             STATUS current
             DESCRIPTION
                "/"
            ::= { hwAcbGroupEquip 1 }

        hwAcbGroupSampEntry OBJECT-TYPE
                        SYNTAX HwAcbGroupSampEntry
            MAX-ACCESS not-accessible
             STATUS current
             DESCRIPTION
                "/"
            INDEX { hwAcbGroupIndex }
            ::= { hwAcbGroupSampTable 1 }

        HwAcbGroupSampEntry            ::= SEQUENCE {
                hwAcbGroupIndex
                    Unsigned32,
                hwAcbGroupEquipId
                    Unsigned32,
                hwAcbGroupEquipName
                    OCTET STRING,
                hwAcbGroupBatRunningState
                    INTEGER,
                hwAcbGroupBatVolt
                    Unsigned32,
                hwAcbGroupBatCurr
                    Integer32,
                hwAcbGroupTotalCapacity
                    Unsigned32,
                hwAcbGroupTotalRemainCapacity
                    Unsigned32,
                hwAcbGroupTemperature
                    Integer32,
                hwAcbGroupBackupTime
                    Unsigned32,
                hwAcbGroupEsmuCommNum
                    Unsigned32,
                hwAcbGroupBatSoh
                    Unsigned32,
                hwAcbGroupTotalDischargeDepth
                    Unsigned32,
                hwAcbGroupCycleTimes
                    Unsigned32,
                hwAcbGroupChargeDischargePower
                    Integer32,
                hwAcbGroupMaxChargeablePower
                    Unsigned32,
                hwAcbGroupTotalChargeableCap
                    Unsigned32,
                hwAcbGroupMaxDischargeablePower
                    Unsigned32,
                hwAcbGroupTotalDischargeableCap
                    Unsigned32
            }

        hwAcbGroupIndex OBJECT-TYPE
            SYNTAX Unsigned32 (0..256)
            MAX-ACCESS read-only
            STATUS current
            DESCRIPTION
                "The battery group equip Index."
            ::= { hwAcbGroupSampEntry 1 }

        hwAcbGroupEquipId OBJECT-TYPE
            SYNTAX Unsigned32
            MAX-ACCESS read-only
            STATUS current
            DESCRIPTION
                "The battery group equip ID no."
            ::= { hwAcbGroupSampEntry 2 }

        hwAcbGroupEquipName OBJECT-TYPE
            SYNTAX OCTET STRING
            MAX-ACCESS read-only
            STATUS current
            DESCRIPTION
                "The battery group equip name."
            ::= { hwAcbGroupSampEntry 3 }

        hwAcbGroupBatRunningState OBJECT-TYPE
            SYNTAX INTEGER
                {
                firstOn(1),
                powerOff(2),
                float(3),
                equal(4),
                dicharge(5),
                charge(6),
                test(7),
                unknown(255)
                }
            MAX-ACCESS read-only
            STATUS current
            DESCRIPTION
                "State of the Battery group unit running state. It is an enumeration type: 
                  If the enumeration value is 1, it indicates the Battery is first on line; 
                  If the enumeration value is 2, it indicates that Battery power off; 
                  If the enumeration value is 3, it indicates  that Battery is on float charging; 
                  If the enumeration value is 4, it indicates that Battery is on equal charging; 
                  If the enumeration value is 5, it indicates that Battery is on discharge; 
                  If the enumeration value is 6, it indicates that Battery is on charge; 
                  If the enumeration value is 7, it indicates that Battery is on test; 
                  If the enumeration value is 255,  it indicates Battery uint operation status unknown. 
                "
            ::= { hwAcbGroupSampEntry 4 }

        hwAcbGroupBatVolt OBJECT-TYPE
            SYNTAX Unsigned32 (0..3000)
            MAX-ACCESS read-only
            STATUS current
            DESCRIPTION
                "The battery volt; Value range: 0.0 to 300.0, 
                unit: V. 
                and the value is accurate to one decimal place (.1).  
                If the value is 2147483647(0x7FFFFFFF), it indicates that the value is invalid."
            ::= { hwAcbGroupSampEntry 5 }

        hwAcbGroupBatCurr OBJECT-TYPE
            SYNTAX Integer32 (-4000000..4000000)
            MAX-ACCESS read-only
            STATUS current
            DESCRIPTION
                "The battery current; Value range: -400000 to 400000, 
                unit: A. 
                and the value is accurate to one decimal place (.1).  
                If the value is 2147483647(0x7FFFFFFF), it indicates that the value is invalid."
            ::= { hwAcbGroupSampEntry 6 }

        hwAcbGroupTotalCapacity OBJECT-TYPE
            SYNTAX Unsigned32 (0..10000000)
            MAX-ACCESS read-only
            STATUS current
            DESCRIPTION
                "The battery total capacity; Value range: 0 to 1000000.0, 
                unit: Ah. 
                and the value is accurate to one decimal place (.1).   
                If the value is 2147483647(0x7FFFFFFF), it indicates that the value is invalid."
            ::= { hwAcbGroupSampEntry 7 }

        hwAcbGroupTotalRemainCapacity OBJECT-TYPE
            SYNTAX Unsigned32 (0..100)
            MAX-ACCESS read-only
            STATUS current
            DESCRIPTION
                "The battery total remain capacity; Value range:0 to 100, 
                unit: %. 
                and  the value is an integer (1). 
                If the value is 2147483647(0x7FFFFFFF), it indicates that the value is invalid."
            ::= { hwAcbGroupSampEntry 8 }

        hwAcbGroupTemperature OBJECT-TYPE
            SYNTAX Integer32 (-500..1000)
            MAX-ACCESS read-only
            STATUS current
            DESCRIPTION
                "The battery temperature; Value range:-50.0 to 100.0, 
                unit: degC. 
                and the value is accurate to one decimal space (.1).
                If the value is 2147483647(0x7FFFFFFF), it indicates that the value is invalid."
            ::= { hwAcbGroupSampEntry 9 }

        hwAcbGroupBackupTime OBJECT-TYPE
            SYNTAX Unsigned32 (0..2560)
            MAX-ACCESS read-only
            STATUS current
            DESCRIPTION
                "The battery backup time; Value range: 0 to 256, 
                unit: h.
                and the value is accurate to one decimal place (.1).   
                If the value is 2147483647(0x7FFFFFFF), it indicates that the value is invalid."
            ::= { hwAcbGroupSampEntry 11 }

        hwAcbGroupEsmuCommNum OBJECT-TYPE
            SYNTAX Unsigned32 (0..768)
            MAX-ACCESS read-only
            STATUS current
            DESCRIPTION
                "The esmu communicate number; 
                Value range: 0 to 768.   
                If the value is 2147483647(0x7FFFFFFF), it indicates that the value is invalid."
            ::= { hwAcbGroupSampEntry 12 }

        hwAcbGroupBatSoh OBJECT-TYPE
            SYNTAX Unsigned32 (0..100)
            MAX-ACCESS read-only
            STATUS current
            DESCRIPTION
                "The battery soh: 0 to 100,  
                unit: %. 
                and the value is an integer. 
                If the value is 2147483647(0x7FFFFFFF), it indicates that the value is invalid."
            ::= { hwAcbGroupSampEntry 13 }

        hwAcbGroupTotalDischargeDepth OBJECT-TYPE
            SYNTAX Unsigned32 (0..100)
            MAX-ACCESS read-only
            STATUS current
            DESCRIPTION
                "The battery total discharge depth; Value range:0 to 100, 
                unit: %. 
                and the value is an integer. 
                If the value is 2147483647(0x7FFFFFFF), it indicates that the value is invalid."
            ::= { hwAcbGroupSampEntry 22 }

        hwAcbGroupCycleTimes OBJECT-TYPE
            SYNTAX Unsigned32 (0..3000000)
            MAX-ACCESS read-only
            STATUS current
            DESCRIPTION
                "Acb battery group cycle times. Value range: 0 to 3000000, and the value is an integer. If the value is 2147483647(0x7FFFFFFF), it indicates that the value is invalid."
            ::= { hwAcbGroupSampEntry 23 }

        hwAcbGroupChargeDischargePower OBJECT-TYPE
            SYNTAX Integer32 (-40000000..40000000)
            MAX-ACCESS read-only
            STATUS current
            DESCRIPTION
                "Charge and discharge power of ACB battery group. Value range: -400000 to 400000, unit: kW."
            ::= { hwAcbGroupSampEntry 24 }

        hwAcbGroupMaxChargeablePower OBJECT-TYPE
            SYNTAX Unsigned32 (0..100000)
            MAX-ACCESS read-only
            STATUS current
            DESCRIPTION
                "Maximum chargeable power of ACB battery group. Value range: 0.0 to 10000.0, unit: kW."
            ::= { hwAcbGroupSampEntry 25 }

        hwAcbGroupTotalChargeableCap OBJECT-TYPE
            SYNTAX Unsigned32 (0..100000)
            MAX-ACCESS read-only
            STATUS current
            DESCRIPTION
                "Total Rechargeable Capacity of ACB battery group. Value range: 0.0 to 10000.0, unit: kWh."
            ::= { hwAcbGroupSampEntry 26 }

        hwAcbGroupMaxDischargeablePower OBJECT-TYPE
            SYNTAX Unsigned32 (0..100000)
            MAX-ACCESS read-only
            STATUS current
            DESCRIPTION
                "Maximum dischargeable power of ACB battery group. Value range: 0.0 to 10000.0, unit: kW."
            ::= { hwAcbGroupSampEntry 27 }

        hwAcbGroupTotalDischargeableCap OBJECT-TYPE
            SYNTAX Unsigned32 (0..100000)
            MAX-ACCESS read-only
            STATUS current
            DESCRIPTION
                "Total dischargeable capacity of ACB battery group. Value range: 0 to 10000, unit: kWh."
            ::= { hwAcbGroupSampEntry 28 }

        hwAcbGroupSetTable OBJECT-TYPE
            SYNTAX SEQUENCE OF HwAcbGroupSetEntry
            MAX-ACCESS not-accessible
             STATUS current
             DESCRIPTION
                "/"
            ::= { hwAcbGroupEquip 2 }

        hwAcbGroupSetEntry OBJECT-TYPE
                        SYNTAX HwAcbGroupSetEntry
            MAX-ACCESS not-accessible
             STATUS current
             DESCRIPTION
                "/"
            INDEX { hwAcbGroupCellNum }
            ::= { hwAcbGroupSetTable 1 }

        HwAcbGroupSetEntry            ::= SEQUENCE {
                hwAcbGroupCellNum
                    Unsigned32,
                hwAcbGroupSetTotalCapacity
                    Unsigned32,
                hwAcbGroupEqualVolt
                    Unsigned32,
                hwAcbGroupFloatVolt
                    Unsigned32,
                hwAcbGroupChargeCurrLimitThr
                    Unsigned32,
                hwAcbGroupOverCurThr
                    Unsigned32,
                hwAcbGroupHighTempThr
                    Unsigned32,
                hwAcbGroupLowTempThr
                    Integer32,
                hwAcbGroupDodToAcidBattery
                    Unsigned32,
                hwAcbGroupDefaultChargeCurrLimitThr
                    Unsigned32,
                hwAcbGroupVppRegulationPower
                    OCTET STRING,
                hwAcbGroupChargeEndEn
                    INTEGER,
                hwAcbGroupChargeEndSOC
                    Unsigned32
            }

        hwAcbGroupCellNum OBJECT-TYPE
            SYNTAX Unsigned32 (1..32)
            MAX-ACCESS read-only
            STATUS current
            DESCRIPTION
                "Battery cell number, can be configued by users. 
                Value range: 1 to 32, 
                If the value is 2147483647(0x7FFFFFFF), it indicates that the value is invalid. 
"
            ::= { hwAcbGroupSetEntry 5 }

        hwAcbGroupSetTotalCapacity OBJECT-TYPE
            SYNTAX Unsigned32 (0..1000000)
            MAX-ACCESS read-only
            STATUS current
            DESCRIPTION
                "Battery total capacity, can be configued by users. 
                Value range: 0 to 1000000, 
                If the value is 2147483647(0x7FFFFFFF), it indicates that the value is invalid. 
                unit:Ah."
            ::= { hwAcbGroupSetEntry 6 }

        hwAcbGroupEqualVolt OBJECT-TYPE
            SYNTAX Unsigned32 (420..580)
            MAX-ACCESS read-write
            STATUS current
            DESCRIPTION
                "Battery equalcharge  voltage, can be configued by users. 
                Value range: 42 to 58, 
                unit: V, 
                and the value is accurate to one decimal space (.1).  
                If the value is 2147483647(0x7FFFFFFF), it indicates that the value is invalid. 
"
            ::= { hwAcbGroupSetEntry 11 }

        hwAcbGroupFloatVolt OBJECT-TYPE
            SYNTAX Unsigned32 (420..580)
            MAX-ACCESS read-write
            STATUS current
            DESCRIPTION
                "Battery floatcharge voltage, can be configued by users. 
                Value range: 42 to 58, 
                unit: V, 
                and the value is accurate to one decimal space (.1).  
                If the value is 2147483647(0x7FFFFFFF), it indicates that the value is invalid. 
"
            ::= { hwAcbGroupSetEntry 12 }

        hwAcbGroupChargeCurrLimitThr OBJECT-TYPE
            SYNTAX Unsigned32 (5..105)
            MAX-ACCESS read-write
            STATUS current
            DESCRIPTION
                "Battery charge limited threhold , can be configued by users. 
                Value range: 0.05 to 1.05, 
                unit: C10, 
                and the value is accurate to two decimal space (.01).  
                If the setting value is beyond the current support range, it will fail.
                If the value is 2147483647(0x7FFFFFFF), it indicates that the value is invalid. "
            ::= { hwAcbGroupSetEntry 13 }

        hwAcbGroupOverCurThr OBJECT-TYPE
            SYNTAX Unsigned32 (15..120)
            MAX-ACCESS read-write
            STATUS current
            DESCRIPTION
                "Battery over charge current limited threhold , can be configued by users. 
                Value range: 0.15 to 1.2, 
                unit: C10, 
                and the value is accurate to one decimal space (.01).  
                If the value is 2147483647(0x7FFFFFFF), it indicates that the value is invalid.
"
            ::= { hwAcbGroupSetEntry 14 }

        hwAcbGroupHighTempThr OBJECT-TYPE
            SYNTAX Unsigned32 (35..70)
            MAX-ACCESS read-write
            STATUS current
            DESCRIPTION
                "Upper threshold of the environment temperature alarm, can be configured by users. 
                Value range: 35 to 70, 
                unit: centigrade (°C), 
                and the value is an integer (1).  
                If the value is 2147483647(0x7FFFFFFF), it indicates that the value is invalid. 
"
            ::= { hwAcbGroupSetEntry 21 }

        hwAcbGroupLowTempThr OBJECT-TYPE
            SYNTAX Integer32 (-50..10)
            MAX-ACCESS read-write
            STATUS current
            DESCRIPTION
                "Lower threshold of the environment temperature alarm, can be configured by users. 
                Value range: -50 to 10, 
                unit: centigrade (degC), 
                and the value is an integer (1).  
                If the value is 2147483647(0x7FFFFFFF), it indicates that the value is invalid. 
"
            ::= { hwAcbGroupSetEntry 22 }

        hwAcbGroupDodToAcidBattery OBJECT-TYPE
            SYNTAX Unsigned32 (5..90)
            MAX-ACCESS read-write
            STATUS current
            DESCRIPTION
                "The lithium battery discharge depth for Acid Battery running; Value range: 5 to 90, unit: %. "
            ::= { hwAcbGroupSetEntry 26 }

        hwAcbGroupDefaultChargeCurrLimitThr OBJECT-TYPE
            SYNTAX Unsigned32 (5..105)
            MAX-ACCESS read-write
            STATUS current
            DESCRIPTION
                "Battery default charge limited threhold , can be configued by users. 
                Value range: 0.05 to 1.05, 
                unit: C10, 
                and the value is accurate to two decimal space (.01).  
                If the setting value is beyond the current support range, it will fail.
                If the value is 2147483647(0x7FFFFFFF), it indicates that the value is invalid. "
            ::= { hwAcbGroupSetEntry 27 }

        hwAcbGroupVppRegulationPower OBJECT-TYPE
            SYNTAX OCTET STRING (SIZE (0..127))
            MAX-ACCESS read-write
            STATUS current
            DESCRIPTION
                "Parameter1: VPP Mode. 0:exit 1:enter.
                Parameter2: VPP Rugulation duration of ACB battery group.Value range: 1 to 36000, integer, unit: s.
                Parameter3: VPP Regulation power of ACB battery group. Value range: -1000 to 1000, input limit to 0.01 accuracy, unit: kW.
                use separator ';' to separate those 3 parameters.
                example: 1;3600;1000;"
            ::= { hwAcbGroupSetEntry 28 }

        hwAcbGroupChargeEndEn OBJECT-TYPE
            SYNTAX INTEGER
                {
                disable(1),
                enable(2),
                unknown(255)
                }
            MAX-ACCESS read-write
            STATUS current
            DESCRIPTION
                "Charge End Enable.
                It is an enumeration value, and users actively set it.
                If the enumeration value is 1, it means to disable the charge end unit;
                If the enumeration value is 2, it means to enable the charge end unit.
                If the enumeration value is 255, it indicates unknown unit.
                When the power-off unit control is not configured."
            ::= { hwAcbGroupSetEntry 29 }

        hwAcbGroupChargeEndSOC OBJECT-TYPE
            SYNTAX Unsigned32 (90..100)
            MAX-ACCESS read-write
            STATUS current
            DESCRIPTION
                "Charge End SOC, only 90%, 95%, 100% can be set.
                Only extended lithium battery cabinets are supported."
            ::= { hwAcbGroupSetEntry 30 }

        hwAcbEquip OBJECT IDENTIFIER ::= { hwSiteMonitorMIBObjects 18 }

        hwAcbBaseTable OBJECT-TYPE
            SYNTAX SEQUENCE OF HwAcbBaseEntry
            MAX-ACCESS not-accessible
             STATUS current
             DESCRIPTION
                "/"
            ::= { hwAcbEquip 1 }

        hwAcbBaseEntry OBJECT-TYPE
                        SYNTAX HwAcbBaseEntry
            MAX-ACCESS not-accessible
             STATUS current
             DESCRIPTION
                "/"
            INDEX { hwAcbIndex }
            ::= { hwAcbBaseTable 1 }

        HwAcbBaseEntry            ::= SEQUENCE {
                hwAcbIndex
                    Unsigned32,
                hwAcbEquipId
                    Unsigned32,
                hwAcbEquipName
                    OCTET STRING,
                hwAcbEquipAddr
                    Unsigned32,
                hwAcbSoftVar
                    OCTET STRING,
                hwAcbFatherEquipname
                    OCTET STRING,
                hwAcbHardwareVersion
                    OCTET STRING,
                hwAcbModel
                    OCTET STRING,
                hwAcbBarCode
                    OCTET STRING
            }

        hwAcbIndex OBJECT-TYPE
            SYNTAX Unsigned32
            MAX-ACCESS read-only
            STATUS current
            DESCRIPTION
                "The battery equip Index."
            ::= { hwAcbBaseEntry 1 }

        hwAcbEquipId OBJECT-TYPE
            SYNTAX Unsigned32
            MAX-ACCESS read-only
            STATUS current
            DESCRIPTION
                "The battery equip ID no."
            ::= { hwAcbBaseEntry 2 }

        hwAcbEquipName OBJECT-TYPE
            SYNTAX OCTET STRING
            MAX-ACCESS read-only
            STATUS current
            DESCRIPTION
                "The battery equip name."
            ::= { hwAcbBaseEntry 3 }

        hwAcbEquipAddr OBJECT-TYPE
            SYNTAX Unsigned32 (0..255)
            MAX-ACCESS read-only
            STATUS current
            DESCRIPTION
                "The battery communica address."
            ::= { hwAcbBaseEntry 4 }

        hwAcbSoftVar OBJECT-TYPE
            SYNTAX OCTET STRING
            MAX-ACCESS read-only
            STATUS current
            DESCRIPTION
                "The Battery software version."
            ::= { hwAcbBaseEntry 5 }

        hwAcbFatherEquipname OBJECT-TYPE
            SYNTAX OCTET STRING
            MAX-ACCESS read-only
            STATUS current
            DESCRIPTION
                "Name of the parent device of the battery father"
            ::= { hwAcbBaseEntry 9 }

        hwAcbHardwareVersion OBJECT-TYPE
            SYNTAX OCTET STRING
            MAX-ACCESS read-only
            STATUS current
            DESCRIPTION
                "The Battery hardware version."
            ::= { hwAcbBaseEntry 11 }

        hwAcbModel OBJECT-TYPE
            SYNTAX OCTET STRING
            MAX-ACCESS read-only
            STATUS current
            DESCRIPTION
                "The Battery model."
            ::= { hwAcbBaseEntry 12 }

        hwAcbBarCode OBJECT-TYPE
            SYNTAX OCTET STRING
            MAX-ACCESS read-only
            STATUS current
            DESCRIPTION
                "The Battery SN."
            ::= { hwAcbBaseEntry 13 }

        hwAcbSampTable OBJECT-TYPE
            SYNTAX SEQUENCE OF HwAcbSampEntry
            MAX-ACCESS not-accessible
             STATUS current
             DESCRIPTION
                "/"
            ::= { hwAcbEquip 2 }

        hwAcbSampEntry OBJECT-TYPE
                        SYNTAX HwAcbSampEntry
            MAX-ACCESS not-accessible
             STATUS current
             DESCRIPTION
                "/"
            INDEX { hwAcbBatVolt }
            ::= { hwAcbSampTable 1 }

        HwAcbSampEntry            ::= SEQUENCE {
                hwAcbBatVolt
                    Unsigned32,
                hwAcbBatCurr
                    Integer32,
                hwAcbRunningStatus
                    INTEGER,
                hwAcbBatSoh
                    Unsigned32,
                hwAcbBatCapacity
                    Unsigned32,
                hwAcbBatCell1Volt
                    Unsigned32,
                hwAcbBatCell2Volt
                    Unsigned32,
                hwAcbBatCell3Volt
                    Unsigned32,
                hwAcbBatCell4Volt
                    Unsigned32,
                hwAcbBatCell5Volt
                    Unsigned32,
                hwAcbBatCell6Volt
                    Unsigned32,
                hwAcbBatCell7Volt
                    Unsigned32,
                hwAcbBatCell8Volt
                    Unsigned32,
                hwAcbBatCell9Volt
                    Unsigned32,
                hwAcbBatCell10Volt
                    Unsigned32,
                hwAcbBatCell11Volt
                    Unsigned32,
                hwAcbBatCell12Volt
                    Unsigned32,
                hwAcbBatCell13Volt
                    Unsigned32,
                hwAcbBatCell14Volt
                    Unsigned32,
                hwAcbBatCell15Volt
                    Unsigned32,
                hwAcbBatCell16Volt
                    Unsigned32,
                hwAcbBatCell17Temp
                    Integer32,
                hwAcbBatCell18Temp
                    Integer32,
                hwAcbBatCell19Temp
                    Integer32,
                hwAcbBatCell20Temp
                    Integer32,
                hwAcbBatCell21Temp
                    Integer32,
                hwAcbBatCell22Temp
                    Integer32,
                hwAcbBatCell1Temp
                    Integer32,
                hwAcbBatCell2Temp
                    Integer32,
                hwAcbBatCell3Temp
                    Integer32,
                hwAcbBatCell4Temp
                    Integer32,
                hwAcbBatCell5Temp
                    Integer32,
                hwAcbBatCell6Temp
                    Integer32,
                hwAcbBatCell7Temp
                    Integer32,
                hwAcbBatCell8Temp
                    Integer32,
                hwAcbBatCell9Temp
                    Integer32,
                hwAcbBatCell10Temp
                    Integer32,
                hwAcbBatCell11Temp
                    Integer32,
                hwAcbBatCell12Temp
                    Integer32,
                hwAcbBatCell13Temp
                    Integer32,
                hwAcbBatCell14Temp
                    Integer32,
                hwAcbBatCell15Temp
                    Integer32,
                hwAcbBatCell16Temp
                    Integer32,
                hwAcbBatCell17Volt
                    Unsigned32,
                hwAcbBatCell18Volt
                    Unsigned32,
                hwAcbBatCell19Volt
                    Unsigned32,
                hwAcbBatCell20Volt
                    Unsigned32,
                hwAcbBatCell21Volt
                    Unsigned32,
                hwAcbBatCell22Volt
                    Unsigned32,
                hwAcbBatCell23Temp
                    Integer32,
                hwAcbBatCell23Volt
                    Unsigned32,
                hwAcbBatSoC
                    Unsigned32
            }

        hwAcbBatVolt OBJECT-TYPE
            SYNTAX Unsigned32 (0..300)
            MAX-ACCESS read-only
            STATUS current
            DESCRIPTION
                "voltage of the battery. It indicates the real-time statistics of the battery on the site. 
                Value range: 0.0 to 30.0, 
                unit: V, 
                and the value is accurate to one decimal place (.1).  
                If the value is 2147483647(0x7FFFFFFF), it indicates that the value is invalid."
            ::= { hwAcbSampEntry 1 }

        hwAcbBatCurr OBJECT-TYPE
            SYNTAX Integer32 (-3000..3000)
            MAX-ACCESS read-only
            STATUS current
            DESCRIPTION
                "Current of the battery. It indicates the real-time statistics of the battery on the site. 
                Value range: -300.0 to 300.0, 
                unit: A, 
                and the value is accurate to one decimal place (.1).  
                If the value is 2147483647(0x7FFFFFFF), it indicates that the value is invalid."
            ::= { hwAcbSampEntry 2 }

        hwAcbRunningStatus OBJECT-TYPE
            SYNTAX INTEGER
                {
                offline(0),
                online(1),
                sleep(2),
                disconnect(3),
                charge(4),
                discharge(5),
                standby(6),
                lowpower(7),
                unknown(255)
                }
            MAX-ACCESS read-only
            STATUS current
            DESCRIPTION
                "Battery charging state, indicates the charging and discharging information about the battery group. It is an enumeration type. 
                If the enumeration value is 0, it indicates a battery  in the Offline state. 
                If the enumeration value is 1, it indicates a battery  in the Online state. 
                If the enumeration value is 2, it indicates a battery  in the Sleep state. 
                If the enumeration value is 3, it indicates a battery  in the disconnect state. 
                If the enumeration value is 4, it indicates a battery  in the Charge state. 
                If the enumeration value is 5, it indicates a battery  in the Discharge state. 
                If the enumeration value is 6, it indicates a battery  in the Standby state. 
                If the enumeration value is 255, it indicates a battery group in the unknown state. "
            ::= { hwAcbSampEntry 3 }

        hwAcbBatSoh OBJECT-TYPE
            SYNTAX Unsigned32 (0..100)
            MAX-ACCESS read-only
            STATUS current
            DESCRIPTION
                "Soh of the battery. It indicates the real-time statistics of the battery on the site. 
                Value range: 0 to 100, 
                unit: %, 
                and the value is an integer (1).  
                If the value is 2147483647(0x7FFFFFFF), it indicates that the value is invalid."
            ::= { hwAcbSampEntry 4 }

        hwAcbBatCapacity OBJECT-TYPE
            SYNTAX Unsigned32 (0..100000)
            MAX-ACCESS read-only
            STATUS current
            DESCRIPTION
                "Capacity of the battery. It indicates the real-time statistics of the battery on the site. 
                Value range: 0 to 10000, 
                unit: Ah, 
                and the value is accurate to one decimal place (.1).  
                If the value is 2147483647(0x7FFFFFFF), it indicates that the value is invalid."
            ::= { hwAcbSampEntry 5 }

        hwAcbBatCell1Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 6 }

        hwAcbBatCell2Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 7 }

        hwAcbBatCell3Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 8 }

        hwAcbBatCell4Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 9 }

        hwAcbBatCell5Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 10 }

        hwAcbBatCell6Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 11 }

        hwAcbBatCell7Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 12 }

        hwAcbBatCell8Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 13 }

        hwAcbBatCell9Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 14 }

        hwAcbBatCell10Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 15 }

        hwAcbBatCell11Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 16 }

        hwAcbBatCell12Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 17 }

        hwAcbBatCell13Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 18 }

        hwAcbBatCell14Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 19 }

        hwAcbBatCell15Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 20 }

        hwAcbBatCell16Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 21 }

        hwAcbBatCell17Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 38 }

        hwAcbBatCell18Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 39 }

        hwAcbBatCell19Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 40 }

        hwAcbBatCell20Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 41 }

        hwAcbBatCell21Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 42 }

        hwAcbBatCell22Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 43 }

        hwAcbBatCell1Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 22 }

        hwAcbBatCell2Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 23 }

        hwAcbBatCell3Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 24 }

        hwAcbBatCell4Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 25 }

        hwAcbBatCell5Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 26 }

        hwAcbBatCell6Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 27 }

        hwAcbBatCell7Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 28 }

        hwAcbBatCell8Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 29 }

        hwAcbBatCell9Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 30 }

        hwAcbBatCell10Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 31 }

        hwAcbBatCell11Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 32 }

        hwAcbBatCell12Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 33 }

        hwAcbBatCell13Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 34 }

        hwAcbBatCell14Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 35 }

        hwAcbBatCell15Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 36 }

        hwAcbBatCell16Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal space (.1).
                If the value is 2147483647(0x7FFFFFFF), it indicates that the value is invalid."
            ::= { hwAcbSampEntry 37 }

        hwAcbBatCell17Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 44 }

        hwAcbBatCell18Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 45 }

        hwAcbBatCell19Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 46 }

        hwAcbBatCell20Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 47 }

        hwAcbBatCell21Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 48 }

        hwAcbBatCell22Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).    
                If the value is 2147483647(0x7FFFFFFF), it indicates that the value is invalid."
            ::= { hwAcbSampEntry 49 }

        hwAcbBatCell23Temp OBJECT-TYPE
            SYNTAX Integer32 (-500..1000)
            MAX-ACCESS read-only
            STATUS current
            DESCRIPTION
                "Temperature of the battery cell. It indicates the real-time statistics of the battery on the site. 
                Value range: -50 to 100, 
                unit: centigrade(degC), 
                and the value is accurate to one decimal space (.1).
                If the value is 2147483647(0x7FFFFFFF), it indicates that the value is invalid."
            ::= { hwAcbSampEntry 50 }

        hwAcbBatCell23Volt OBJECT-TYPE
            SYNTAX Unsigned32 (0..500)
            MAX-ACCESS read-only
            STATUS current
            DESCRIPTION
                "Voltage of the battery cell. It indicates the real-time statistics of the battery on the site. 
                Value range: 0 to 5, 
                unit: V, 
                and the value is accurate to two decimal place (.01).  
                If the value is 2147483647(0x7FFFFFFF), it indicates that the value is invalid."
            ::= { hwAcbSampEntry 51 }

        hwAcbBatSoC OBJECT-TYPE
            SYNTAX Unsigned32 (0..100)
            MAX-ACCESS read-only
            STATUS current
            DESCRIPTION
                "SoC of the battery. It indicates the real-time statistics of the battery on the site. 
                Value range: 0 to 100, 
                unit: %, 
                and the value is an integer (1).  
                If the value is 2147483647(0x7FFFFFFF), it indicates that the value is invalid."
            ::= { hwAcbSampEntry 52 }

        hwAcbSetTable OBJECT-TYPE
            SYNTAX SEQUENCE OF HwAcbSetEntry
            MAX-ACCESS not-accessible
             STATUS current
             DESCRIPTION
                "/"
            ::= { hwAcbEquip 3 }

        hwAcbSetEntry OBJECT-TYPE
                        SYNTAX HwAcbSetEntry
            MAX-ACCESS not-accessible
             STATUS current
             DESCRIPTION
                "/"
            INDEX { hwAcbCtlOnOff }
            ::= { hwAcbSetTable 1 }

        HwAcbSetEntry            ::= SEQUENCE {
                hwAcbCtlOnOff
                    INTEGER,
                hwAcbGyroEnable
                    INTEGER,
                hwAcbGyroSensitivityLevel
                    INTEGER,
                hwAcbVendorName
                    OCTET STRING,
                hwAcbManufactured
                    OCTET STRING,
                hwAcbSelfStaggerDOD
                    Unsigned32
            }

        hwAcbCtlOnOff OBJECT-TYPE
            SYNTAX INTEGER
                {
                on(1),
                off(2),
                unknown(255)
                }
            MAX-ACCESS read-write
            STATUS current
            DESCRIPTION
                "Control power on/off. It is an enumeration value, and users actively set it. If the enumeration value is 1, it means to power off; If the enumeration value is 2, it means to power on; If the enumeration value is 255, it indicates a battery group in the unknown state."
            ::= { hwAcbSetEntry 2 }

        hwAcbGyroEnable OBJECT-TYPE
            SYNTAX INTEGER
                {
                disable(0),
                enable(1),
                unknown(255)
                }
            MAX-ACCESS read-write
            STATUS current
            DESCRIPTION
                "Gyro Function Enable, 
                Restricted use in special areas. If the value of the device is within the range, but the setting fails, the function is not supported.
                It is an enumeration value: 
                If the enumeration value is 0, it means to gyro function disable,
                If the enumeration value is 1, it means to gyro function enable,
                If the enumeration value is 255, it indicates gyro in the unknown state."
            ::= { hwAcbSetEntry 5 }

        hwAcbGyroSensitivityLevel OBJECT-TYPE
            SYNTAX INTEGER
                {
                low(0),
                midium(1),
                high(2),
                unknown(255)
                }
            MAX-ACCESS read-write
            STATUS current
            DESCRIPTION
                "Gyro Level of Sensitivity.
                Restricted use in special areas. If the value of the device is within the range, but the setting fails, the function is not supported.
                It is an enumeration value:
                If the enumeration value is 0, it means to low sensitivity,
                If the enumeration value is 1, it means to medium sensitivity,
                If the enumeration value is 2, it means to high sensitivity,
                If the enumeration value is 255, it indicates gyro in the unknown level."
            ::= { hwAcbSetEntry 6 }

        hwAcbVendorName OBJECT-TYPE
            SYNTAX OCTET STRING
            MAX-ACCESS read-write
            STATUS current
            DESCRIPTION
                "Battery vendor name,can be configured by users.
                "
            ::= { hwAcbSetEntry 7 }

        hwAcbManufactured OBJECT-TYPE
            SYNTAX OCTET STRING
            MAX-ACCESS read-write
            STATUS current
            DESCRIPTION
                "Battery manufacturing date,can be configured by users, and the setting style reference is YYYY-MM-DD."
            ::= { hwAcbSetEntry 8 }

        hwAcbSelfStaggerDOD OBJECT-TYPE
            SYNTAX Unsigned32 (0..100)
            MAX-ACCESS read-write
            STATUS current
            DESCRIPTION
                "Self stagger DOD value of ACB battery. Value range: 0 to 100, unit: %, and the value is an interger. Default value is 50%."
            ::= { hwAcbSetEntry 9 }

        hwElockEquip OBJECT IDENTIFIER ::= { hwSiteMonitorMIBObjects 27 }

        hwElockEquipTable OBJECT-TYPE
            SYNTAX SEQUENCE OF HwElockEquipEntry
            MAX-ACCESS not-accessible
             STATUS current
             DESCRIPTION
                "/"
            ::= { hwElockEquip 1 }

        hwElockEquipEntry OBJECT-TYPE
                        SYNTAX HwElockEquipEntry
            MAX-ACCESS not-accessible
             STATUS current
             DESCRIPTION
                "/"
            INDEX { hwElockEquipIndex }
            ::= { hwElockEquipTable 1 }

        HwElockEquipEntry            ::= SEQUENCE {
                hwElockEquipIndex
                    Unsigned32,
                hwElockEquipId
                    Unsigned32,
                hwElockEquipName
                    OCTET STRING,
                hwElockFatherEquipName
                    OCTET STRING
            }

        hwElockEquipIndex OBJECT-TYPE
            SYNTAX Unsigned32
            MAX-ACCESS read-only
            STATUS current
            DESCRIPTION
                "The elock equip Index."
            ::= { hwElockEquipEntry 1 }

        hwElockEquipId OBJECT-TYPE
            SYNTAX Unsigned32
            MAX-ACCESS read-only
            STATUS current
            DESCRIPTION
                "The elock  equip ID no."
            ::= { hwElockEquipEntry 2 }

        hwElockEquipName OBJECT-TYPE
            SYNTAX OCTET STRING (SIZE (0..63))
            MAX-ACCESS read-only
            STATUS current
            DESCRIPTION
                " The elock equip name."
            ::= { hwElockEquipEntry 3 }

        hwElockFatherEquipName OBJECT-TYPE
            SYNTAX OCTET STRING (SIZE (0..63))
            MAX-ACCESS read-only
            STATUS current
            DESCRIPTION
                " Father device name of the elock equip. "
            ::= { hwElockEquipEntry 4 }

        hwTemHumEquip OBJECT IDENTIFIER ::= { hwSiteMonitorMIBObjects 28 }

        hwTemHumEquipTable OBJECT-TYPE
            SYNTAX SEQUENCE OF HwTemHumEquipEntry
            MAX-ACCESS not-accessible
             STATUS current
             DESCRIPTION
                "/"
            ::= { hwTemHumEquip 1 }

        hwTemHumEquipEntry OBJECT-TYPE
                        SYNTAX HwTemHumEquipEntry
            MAX-ACCESS not-accessible
             STATUS current
             DESCRIPTION
                "/"
            INDEX { hwTemHumEquipIndex }
            ::= { hwTemHumEquipTable 1 }

        HwTemHumEquipEntry            ::= SEQUENCE {
                hwTemHumEquipIndex
                    Unsigned32,
                hwTemHumEquipId
                    Unsigned32,
                hwTemHumEquipName
                    OCTET STRING,
                hwTemHumEquipAmbientTemp
                    Integer32,
                hwTemHumEquipAmbientHumidity
                    Unsigned32,
                hwSetHumTempUpperLimit
                    Integer32,
                hwSetHumTempLowerLimit
                    Integer32,
                hwSetHumidityUpperLimit
                    Integer32,
                hwSetHumidityLowerLimit
                    Integer32,
                hwTemHumEquipAddress
                    Unsigned32,
                hwTemHumFahterEquipName
                    OCTET STRING
            }

        hwTemHumEquipIndex OBJECT-TYPE
            SYNTAX Unsigned32
            MAX-ACCESS read-only
            STATUS current
            DESCRIPTION
                "The tem_hum equip Index."
            ::= { hwTemHumEquipEntry 1 }

        hwTemHumEquipId OBJECT-TYPE
            SYNTAX Unsigned32
            MAX-ACCESS read-only
            STATUS current
            DESCRIPTION
                "The tem_hum  equip ID no."
            ::= { hwTemHumEquipEntry 2 }

        hwTemHumEquipName OBJECT-TYPE
            SYNTAX OCTET STRING (SIZE (0..63))
            MAX-ACCESS read-only
            STATUS current
            DESCRIPTION
                " The tem_hum equip name."
            ::= { hwTemHumEquipEntry 3 }

        hwTemHumEquipAmbientTemp OBJECT-TYPE
            SYNTAX Integer32 (-20..80)
            MAX-ACCESS read-only
            STATUS current
            DESCRIPTION
                "the environment temperature. 
                unit: centigrade (degC), 
                and the value is an integer (1).  "
            ::= { hwTemHumEquipEntry 4 }

        hwTemHumEquipAmbientHumidity OBJECT-TYPE
            SYNTAX Unsigned32 (0..100)
            MAX-ACCESS read-only
            STATUS current
            DESCRIPTION
                "environment humidity , 
                unit: %, 
                and the value is an integer (1).  "
            ::= { hwTemHumEquipEntry 5 }

        hwSetHumTempUpperLimit OBJECT-TYPE
            SYNTAX Integer32 ( 25..80)
            MAX-ACCESS read-write
            STATUS current
            DESCRIPTION
                "Upper threshold of the environment temperature alarm, can be configured by users. 
                Value range: 25 to 80, 
                unit: centigrade (degC), 
                and the value is an integer (1). 
                If the value is 2147483647(0x7FFFFFFF), it indicates that the value is invalid.
                NOTE: There is linkage between hwSetHumTempUpperLimit and hwSetHumTempLowerLimit"
            ::= { hwTemHumEquipEntry 6 }

        hwSetHumTempLowerLimit OBJECT-TYPE
            SYNTAX Integer32 ( -20..20)
            MAX-ACCESS read-write
            STATUS current
            DESCRIPTION
                "Lower threshold of the environment temperature alarm, can be configured by users. 
                Value range: -20 to 20, 
                unit: centigrade (degC), 
                and the value is an integer (1).  
                If the value is 2147483647(0x7FFFFFFF), it indicates that the value is invalid.
                NOTE: There is linkage between hwSetHumTempUpperLimit and hwSetHumTempLowerLimit"
            ::= { hwTemHumEquipEntry 7 }

        hwSetHumidityUpperLimit OBJECT-TYPE
            SYNTAX Integer32 (0..100)
            MAX-ACCESS read-write
            STATUS current
            DESCRIPTION
                "Upper threshold of the environment humility alarm, can be configured by users. 
                Value range: 0 to 100, 
                unit: %, 
                and the value is an integer (1).  
                If the value is 2147483647(0x7FFFFFFF), it indicates that the value is invalid."
            ::= { hwTemHumEquipEntry 8 }

        hwSetHumidityLowerLimit OBJECT-TYPE
            SYNTAX Integer32 (0..100)
            MAX-ACCESS read-write
            STATUS current
            DESCRIPTION
                "Lower threshold of the environment humility alarm, can be configured by users. 
                Value range: 0 to 100, 
                unit: %, 
                and the value is an integer (1).  
                If the value is 2147483647(0x7FFFFFFF), it indicates that the value is invalid."
            ::= { hwTemHumEquipEntry 9 }

        hwTemHumEquipAddress OBJECT-TYPE
            SYNTAX Unsigned32 (0..255)
            MAX-ACCESS read-only
            STATUS current
            DESCRIPTION
                "Device address
                And the value is an integer (1)."
            ::= { hwTemHumEquipEntry 10 }

        hwTemHumFahterEquipName OBJECT-TYPE
            SYNTAX OCTET STRING (SIZE (0..63))
            MAX-ACCESS read-only
            STATUS current
            DESCRIPTION
                " Father device name of the tem_hum equip. "
            ::= { hwTemHumEquipEntry 12 }

        hwHeaterEquip OBJECT IDENTIFIER ::= { hwSiteMonitorMIBObjects 29 }

        hwHeaterDeviceTable OBJECT-TYPE
            SYNTAX SEQUENCE OF HwHeaterDeviceEntry
            MAX-ACCESS not-accessible
             STATUS current
             DESCRIPTION
                ""
            ::= { hwHeaterEquip 1 }

        hwHeaterDeviceEntry OBJECT-TYPE
                        SYNTAX HwHeaterDeviceEntry
            MAX-ACCESS not-accessible
             STATUS current
             DESCRIPTION
                ""
            INDEX { hwHeaterDeviceIndex }
            ::= { hwHeaterDeviceTable 1 }

        HwHeaterDeviceEntry            ::= SEQUENCE {
                hwHeaterDeviceIndex
                    Unsigned32,
                hwHeaterDeviceEquipId
                    Unsigned32,
                hwHeaterDeviceEquipName
                    OCTET STRING,
                hwHeaterStartTemperature
                    Integer32,
                hwHeaterStopTemperature
                    Integer32,
                hwHeaterDeviceFatherEquipName
                    OCTET STRING
            }

        hwHeaterDeviceIndex OBJECT-TYPE
            SYNTAX Unsigned32
            MAX-ACCESS read-only
            STATUS current
            DESCRIPTION
                "heater device table index."
            ::= { hwHeaterDeviceEntry 1 }

        hwHeaterDeviceEquipId OBJECT-TYPE
            SYNTAX Unsigned32
            MAX-ACCESS read-only
            STATUS current
            DESCRIPTION
                "heater device equipid."
            ::= { hwHeaterDeviceEntry 2 }

        hwHeaterDeviceEquipName OBJECT-TYPE
            SYNTAX OCTET STRING (SIZE (0..63))
            MAX-ACCESS read-only
            STATUS current
            DESCRIPTION
                "heater device equipname."
            ::= { hwHeaterDeviceEntry 3 }

        hwHeaterStartTemperature OBJECT-TYPE
            SYNTAX Integer32 (-10..15)
            MAX-ACCESS read-write
            STATUS current
            DESCRIPTION
                "heater start temperature;
                Value range:-10 to 15.Unit: degC.
                and the value is an integer (1).  
                If the value is 2147483647(0x7FFFFFFF), it indicates that the value is invalid. 
                note: hwHeaterStartTemperature's set value must below hwHeaterStopTemperature's value."
            ::= { hwHeaterDeviceEntry 4 }

        hwHeaterStopTemperature OBJECT-TYPE
            SYNTAX Integer32 (5..20)
            MAX-ACCESS read-write
            STATUS current
            DESCRIPTION
                "heater stop temperature;
                Value range: 5 to 20.Unit: degC.
                and the value is an integer (1).  
                If the value is 2147483647(0x7FFFFFFF), it indicates that the value is invalid.
                note: hwHeaterStartTemperature's set value must below hwHeaterStopTemperature's value."
            ::= { hwHeaterDeviceEntry 5 }

        hwHeaterDeviceFatherEquipName OBJECT-TYPE
            SYNTAX OCTET STRING (SIZE (0..63))
            MAX-ACCESS read-only
            STATUS current
            DESCRIPTION
                " Father device name of the heater equip. "
            ::= { hwHeaterDeviceEntry 6 }

        hwSiteDCDB OBJECT IDENTIFIER ::= { hwSiteMonitorMIBObjects 31 }

        hwSiteDCDBSampTable OBJECT-TYPE
            SYNTAX SEQUENCE OF HwSiteDCDBSampEntry
            MAX-ACCESS not-accessible
             STATUS current
             DESCRIPTION
                ""
            ::= { hwSiteDCDB 1 }

        hwSiteDCDBSampEntry OBJECT-TYPE
                        SYNTAX HwSiteDCDBSampEntry
            MAX-ACCESS not-accessible
             STATUS current
             DESCRIPTION
                ""
            INDEX { hwDCDBIndex }
            ::= { hwSiteDCDBSampTable 1 }

        HwSiteDCDBSampEntry            ::= SEQUENCE {
                hwDCDBIndex
                    Unsigned32,
                hwDCDBEquipId
                    Unsigned32,
                hwDCDBEquipName
                    OCTET STRING,
                hwDCDBDCOutputVoltage
                    Unsigned32,
                hwDCDBLoadCurrent
                    Integer32,
                hwDCDBTotalLoadConsumption
                    Unsigned32,
                hwDCDBLoad1Current
                    Integer32,
                hwDCDBLoad2Current
                    Integer32,
                hwDCDBLoadTotalPower
                    Unsigned32,
                hwDCDBLoad1TotalPower
                    Unsigned32,
                hwDCDBLoad2TotalPower
                    Unsigned32,
                hwDCDBLoad1PowerConsumption
                    Unsigned32,
                hwDCDBLoad2PowerConsumption
                    Unsigned32
            }

        hwDCDBIndex OBJECT-TYPE
            SYNTAX Unsigned32 (0..256)
            MAX-ACCESS read-only
            STATUS current
            DESCRIPTION
                "DCDB table index,
                which value range:1 to 256. 
                Lines of the device list are restricted by the quantity of DMU."
            ::= { hwSiteDCDBSampEntry 1 }

        hwDCDBEquipId OBJECT-TYPE
            SYNTAX Unsigned32 (33001..33255)
            MAX-ACCESS read-only
            STATUS current
            DESCRIPTION
                "DMU device ID. 
                Value range: 033'001 to 033'255, 
                in which the first digits indicate the device type and the last three digits indicate the device SN."
            ::= { hwSiteDCDBSampEntry 2 }

        hwDCDBEquipName OBJECT-TYPE
            SYNTAX OCTET STRING (SIZE (0..56))
            MAX-ACCESS read-only
            STATUS current
            DESCRIPTION
                "Device name of the DCDB module, 
                character string type, is used to specify the DMU module. Otherwise, the configured character can not be any other languages except English."
            ::= { hwSiteDCDBSampEntry 3 }

        hwDCDBDCOutputVoltage OBJECT-TYPE
            SYNTAX Unsigned32 (0..1000)
            MAX-ACCESS read-only
            STATUS current
            DESCRIPTION
                "DC output voltage: 0 to 100, 
                unit: V, 
                and the value is one decimal space (.1). If the value is 2147483647(0x7FFFFFFF), it indicates that the value is invalid."
            ::= { hwSiteDCDBSampEntry 4 }

        hwDCDBLoadCurrent OBJECT-TYPE
            SYNTAX Integer32 (-300000..300000)
            MAX-ACCESS read-only
            STATUS current
            DESCRIPTION
                "Load current: -30000.0 to 30000.0, 
                unit: A, 
                and the value is one decimal space (.1). If the value is 2147483647(0x7FFFFFFF), it indicates that the value is invalid."
            ::= { hwSiteDCDBSampEntry 5 }

        hwDCDBTotalLoadConsumption OBJECT-TYPE
            SYNTAX Unsigned32 (0..4294967295)
            MAX-ACCESS read-only
            STATUS current
            DESCRIPTION
                "Total load consumption: 0 to 4294967295, 
                unit: kWh, 
                and the value is one decimal space (.1). 
                If the value is 2147483647(0x7FFFFFFF), it indicates that the value is invalid."
            ::= { hwSiteDCDBSampEntry 6 }

        hwDCDBLoad1Current OBJECT-TYPE
            SYNTAX Integer32 (-300000..300000)
            MAX-ACCESS read-only
            STATUS current
            DESCRIPTION
                "Load 1 current of DCDB. Value range: -300000 to 300000, unit: A, and the value is accurate to one decimal place (.1)."
            ::= { hwSiteDCDBSampEntry 7 }

        hwDCDBLoad2Current OBJECT-TYPE
            SYNTAX Integer32 (-300000..300000)
            MAX-ACCESS read-only
            STATUS current
            DESCRIPTION
                "Load 2 current of DCDB. Value range: -300000 to 300000, unit: A, and the value is accurate to one decimal place (.1)."
            ::= { hwSiteDCDBSampEntry 8 }

        hwDCDBLoadTotalPower OBJECT-TYPE
            SYNTAX Unsigned32 (0..300000)
            MAX-ACCESS read-only
            STATUS current
            DESCRIPTION
                "Total load power of DCDB. Value range: 0 to 300000, unit: kW, and the value is accurate to two decimal place (.01)."
            ::= { hwSiteDCDBSampEntry 9 }

        hwDCDBLoad1TotalPower OBJECT-TYPE
            SYNTAX Unsigned32 (0..300000)
            MAX-ACCESS read-only
            STATUS current
            DESCRIPTION
                "Load 1 total power of DCDB. Value range: 0 to 300000, unit: kW, and the value is accurate to two decimal place (.01)."
            ::= { hwSiteDCDBSampEntry 10 }

        hwDCDBLoad2TotalPower OBJECT-TYPE
            SYNTAX Unsigned32 (0..300000)
            MAX-ACCESS read-only
            STATUS current
            DESCRIPTION
                "Load 1 total power of DCDB. Value range: 0 to 300000, unit: kW, and the value is accurate to two decimal place (.01)."
            ::= { hwSiteDCDBSampEntry 11 }

        hwDCDBLoad1PowerConsumption OBJECT-TYPE
            SYNTAX Unsigned32 (0..4294967295)
            MAX-ACCESS read-only
            STATUS current
            DESCRIPTION
                "Load 1 power consumption of DCDB. Value range: 0 to 429496729500, unit: kWh, and the value is accurate to two decimal place (.01)."
            ::= { hwSiteDCDBSampEntry 12 }

        hwDCDBLoad2PowerConsumption OBJECT-TYPE
            SYNTAX Unsigned32 (0..4294967295)
            MAX-ACCESS read-only
            STATUS current
            DESCRIPTION
                "Load 1 power consumption of DCDB. Value range: 0 to 429496729500, unit: kWh, and the value is accurate to two decimal place (.01)."
            ::= { hwSiteDCDBSampEntry 13 }

        hwSiteDCDBSetTable OBJECT-TYPE
            SYNTAX SEQUENCE OF HwSiteDCDBSetEntry
            MAX-ACCESS not-accessible
             STATUS current
             DESCRIPTION
                ""
            ::= { hwSiteDCDB 2 }

        hwSiteDCDBSetEntry OBJECT-TYPE
                        SYNTAX HwSiteDCDBSetEntry
            MAX-ACCESS not-accessible
             STATUS current
             DESCRIPTION
                ""
            INDEX { hwSiteDCDBLoad1LvdEn }
            ::= { hwSiteDCDBSetTable 1 }

        HwSiteDCDBSetEntry            ::= SEQUENCE {
                hwSiteDCDBLoad1LvdEn
                    INTEGER,
                hwSiteDCDBLoad1LvdMode
                    INTEGER,
                hwSiteDCDBLoad1LvdVoltage
                    Unsigned32,
                hwSiteDCDBLoad1LvdReconVoltage
                    Unsigned32,
                hwSiteDCDBLoad1LvdTime
                    Integer32,
                hwSiteDCDBLoad1LvdCapacity
                    Integer32,
                hwSiteDCDBLoad2LvdEn
                    INTEGER,
                hwSiteDCDBLoad2LvdMode
                    INTEGER,
                hwSiteDCDBLoad2LvdVoltage
                    Unsigned32,
                hwSiteDCDBLoad2LvdReconVoltage
                    Unsigned32,
                hwSiteDCDBLoad2LvdTime
                    Integer32,
                hwSiteDCDBLoad2LvdCapacity
                    Integer32,
                hwSiteDCDBSetLLVD1PowerOffConsumption
                    Unsigned32,
                hwSiteDCDBSetLLVD2PowerOffConsumption
                    Unsigned32,
                hwSiteDCDBReset
                    INTEGER,
                hwSiteDCDBLoadOffAlmDelayTime
                    Unsigned32,
                hwSiteDCDBDinLLVD1Enable
                    INTEGER,
                hwSiteDCDBDinLLVD1Index
                    INTEGER,
                hwSiteDCDBDinLLVD1Condition
                    INTEGER,
                hwSiteDCDBDinLLVD1Delay
                    Unsigned32,
                hwSiteDCDBDinLLVD2Enable
                    INTEGER,
                hwSiteDCDBDinLLVD2Index
                    INTEGER,
                hwSiteDCDBDinLLVD2Condition
                    INTEGER,
                hwSiteDCDBDinLLVD2Delay
                    Unsigned32,
                hwSiteDCDBSetLoad1UserConfig
                    INTEGER,
                hwSiteDCDBSetLoad2UserConfig
                    INTEGER,
                hwSiteDCDBSetPowerSupplySource
                    INTEGER,
                hwSiteDCDBSetLLVD1EnableForPeakShaving
                    INTEGER,
                hwSiteDCDBSetLLVD2EnableForPeakShaving
                    INTEGER,
                hwSiteDCDBSetLLVD1TimingOnOffEnable
                    INTEGER,
                hwSiteDCDBSetLLVD1TimingOnOffStartTime1
                    OCTET STRING,
                hwSiteDCDBSetLLVD1TimedDuration1
                    Unsigned32,
                hwSiteDCDBSetLLVD1TimingOnOffStartTime2
                    OCTET STRING,
                hwSiteDCDBSetLLVD1TimedDuration2
                    Unsigned32,
                hwSiteDCDBSetLLVD1TimingOnOffStartTime3
                    OCTET STRING,
                hwSiteDCDBSetLLVD1TimedDuration3
                    Unsigned32,
                hwSiteDCDBSetLLVD1TimingOnOffStartTime4
                    OCTET STRING,
                hwSiteDCDBSetLLVD1TimedDuration4
                    Unsigned32,
                hwSiteDCDBSetLLVD1TimingOnOffStartTime5
                    OCTET STRING,
                hwSiteDCDBSetLLVD1TimedDuration5
                    Unsigned32,
                hwSiteDCDBSetLLVD2TimingOnOffEnable
                    INTEGER,
                hwSiteDCDBSetLLVD2TimingOnOffStartTime1
                    OCTET STRING,
                hwSiteDCDBSetLLVD2TimedDuration1
                    Unsigned32,
                hwSiteDCDBSetLLVD2TimingOnOffStartTime2
                    OCTET STRING,
                hwSiteDCDBSetLLVD2TimedDuration2
                    Unsigned32,
                hwSiteDCDBSetLLVD2TimingOnOffStartTime3
                    OCTET STRING,
                hwSiteDCDBSetLLVD2TimedDuration3
                    Unsigned32,
                hwSiteDCDBSetLLVD2TimingOnOffStartTime4
                    OCTET STRING,
                hwSiteDCDBSetLLVD2TimedDuration4
                    Unsigned32,
                hwSiteDCDBSetLLVD2TimingOnOffStartTime5
                    OCTET STRING,
                hwSiteDCDBSetLLVD2TimedDuration5
                    Unsigned32,
                hwSiteDCDBSetLLVD1ExemptPeriodOnOffEnable
                    INTEGER,
                hwSiteDCDBSetLLVD1ExemptPeriodOnOffStartTime1
                    OCTET STRING,
                hwSiteDCDBSetLLVD1ExemptDuration1
                    Unsigned32,
                hwSiteDCDBSetLLVD1ExemptPeriodOnOffStartTime2
                    OCTET STRING,
                hwSiteDCDBSetLLVD1ExemptDuration2
                    Unsigned32,
                hwSiteDCDBSetLLVD1ExemptPeriodOnOffStartTime3
                    OCTET STRING,
                hwSiteDCDBSetLLVD1ExemptDuration3
                    Unsigned32,
                hwSiteDCDBSetLLVD1ExemptPeriodOnOffStartTime4
                    OCTET STRING,
                hwSiteDCDBSetLLVD1ExemptDuration4
                    Unsigned32,
                hwSiteDCDBSetLLVD1ExemptPeriodOnOffStartTime5
                    OCTET STRING,
                hwSiteDCDBSetLLVD1ExemptDuration5
                    Unsigned32,
                hwSiteDCDBSetLLVD2ExemptPeriodOnOffEnable
                    INTEGER,
                hwSiteDCDBSetLLVD2ExemptPeriodOnOffStartTime1
                    OCTET STRING,
                hwSiteDCDBSetLLVD2ExemptDuration1
                    Unsigned32,
                hwSiteDCDBSetLLVD2ExemptPeriodOnOffStartTime2
                    OCTET STRING,
                hwSiteDCDBSetLLVD2ExemptDuration2
                    Unsigned32,
                hwSiteDCDBSetLLVD2ExemptPeriodOnOffStartTime3
                    OCTET STRING,
                hwSiteDCDBSetLLVD2ExemptDuration3
                    Unsigned32,
                hwSiteDCDBSetLLVD2ExemptPeriodOnOffStartTime4
                    OCTET STRING,
                hwSiteDCDBSetLLVD2ExemptDuration4
                    Unsigned32,
                hwSiteDCDBSetLLVD2ExemptPeriodOnOffStartTime5
                    OCTET STRING,
                hwSiteDCDBSetLLVD2ExemptDuration5
                    Unsigned32,
                hwSiteDCDBSetLLVD1DGOff
                    INTEGER,
                hwSiteDCDBSetLLVD2DGOff
                    INTEGER
            }

        hwSiteDCDBLoad1LvdEn OBJECT-TYPE
            SYNTAX INTEGER
                {
                disable(1),
                enable(2)
                }
            MAX-ACCESS read-write
            STATUS current
            DESCRIPTION
                "load1 lvd enable :It is an enumeration type: 
                  If the enumeration value is 1, it means to disable the lvd control; 
                  If the enumeration value is 2, it means to enable the lvd control "
            ::= { hwSiteDCDBSetEntry 1 }

        hwSiteDCDBLoad1LvdMode OBJECT-TYPE
            SYNTAX INTEGER
                {
                voltagemode(1),
                timemode(2),
                capacitymode(3),
                powermode(4),
                unknown(255)
                }
            MAX-ACCESS read-write
            STATUS current
            DESCRIPTION
                "load1 lvd mode :It is an enumeration type: 
                  If the enumeration value is 1, it means the voltage mode; 
                  If the enumeration value is 2, it means the time mode "
            ::= { hwSiteDCDBSetEntry 2 }

        hwSiteDCDBLoad1LvdVoltage OBJECT-TYPE
            SYNTAX Unsigned32 (360..560)
            MAX-ACCESS read-write
            STATUS current
            DESCRIPTION
                "Low-voltage power-off voltage of the DCDB unit can be configured by users. 
                Its value range: 36 to 56, 
                unit: V, 
                and the value is accurate to one decimal space (.1).  
                If the value is 2147483647(0x7FFFFFFF), it indicates that the value is invalid."
            ::= { hwSiteDCDBSetEntry 3 }

        hwSiteDCDBLoad1LvdReconVoltage OBJECT-TYPE
            SYNTAX Unsigned32 (370..580)
            MAX-ACCESS read-write
            STATUS current
            DESCRIPTION
                "Low-voltage power-off recover of the DCDB unit can be configured by users. 
                Its value range: 37.0 to 58.0, 
                unit: V, 
                and the value is accurate to one decimal space (.1).  If the value is 2147483647(0x7FFFFFFF), it indicates that the value is invalid.
                NOTE: There is linkage between hwSiteDMULoad1LvdVoltage and hwSiteDMULoad1LvdReconVoltage"
            ::= { hwSiteDCDBSetEntry 4 }

        hwSiteDCDBLoad1LvdTime OBJECT-TYPE
            SYNTAX Integer32 (0..6000)
            MAX-ACCESS read-write
            STATUS current
            DESCRIPTION
                "Low-voltage power-off disconnected time, It can be configured by users, and its value is an integer (1). 
                Here, if lvd mode is time mode, value range defines between 0 to 6000, 
                unit: minutes(min). 
                If the value is 2147483647(0x7FFFFFFF), it indicates that the value is invalid.
                NOTE: Only the lvd in time power off mode, this parameter can be configured successfully."
            ::= { hwSiteDCDBSetEntry 5 }

        hwSiteDCDBLoad1LvdCapacity OBJECT-TYPE
            SYNTAX Integer32 (0..99)
            MAX-ACCESS read-write
            STATUS current
            DESCRIPTION
                "Power-off unit control the power off, when Remaining capacity percentage of the battery strings is below the calue. 
                Value range: 0 to 99, 
                unit: %, 
                and the value is accurate to one decimal place (.1).  If the value is 2147483647(0x7FFFFFFF), it indicates that the value is invalid.
                NOTE: Only the lvd in capacity power off mode, this parameter can be configured successfully."
            ::= { hwSiteDCDBSetEntry 6 }

        hwSiteDCDBLoad2LvdEn OBJECT-TYPE
            SYNTAX INTEGER
                {
                disable(1),
                enable(2)
                }
            MAX-ACCESS read-write
            STATUS current
            DESCRIPTION
                "load1 lvd enable :It is an enumeration type: 
                If the enumeration value is 1, it means to disable the lvd control; 
                If the enumeration value is 2, it means to enable the lvd control "
            ::= { hwSiteDCDBSetEntry 7 }

        hwSiteDCDBLoad2LvdMode OBJECT-TYPE
            SYNTAX INTEGER
                {
                voltagemode(1),
                timemode(2),
                capacitymode(3),
                powermode(4),
                unknown(255)
                }
            MAX-ACCESS read-write
            STATUS current
            DESCRIPTION
                "load1 lvd mode :It is an enumeration type: 
                If the enumeration value is 1, it means the voltage mode; 
                If the enumeration value is 2, it means the time mode "
            ::= { hwSiteDCDBSetEntry 8 }

        hwSiteDCDBLoad2LvdVoltage OBJECT-TYPE
            SYNTAX Unsigned32 (360..560)
            MAX-ACCESS read-write
            STATUS current
            DESCRIPTION
                "Low-voltage power-off voltage of the DCDB unit can be configured by users. 
                Its value range: 36 to 56, 
                unit: V, 
                and the value is accurate to one decimal space (.1).  
                If the value is 2147483647(0x7FFFFFFF), it indicates that the value is invalid."
            ::= { hwSiteDCDBSetEntry 9 }

        hwSiteDCDBLoad2LvdReconVoltage OBJECT-TYPE
            SYNTAX Unsigned32 (370..580)
            MAX-ACCESS read-write
            STATUS current
            DESCRIPTION
                "Low-voltage power-off recover of the DCDB unit can be configured by users. 
                Its value range: 37.0 to 58.0, 
                unit: V, 
                and the value is accurate to one decimal space (.1).  If the value is 2147483647(0x7FFFFFFF), it indicates that the value is invalid.
                NOTE: There is linkage between hwSiteDMULoad2LvdVoltage and hwSiteDMULoad2LvdReconVoltage"
            ::= { hwSiteDCDBSetEntry 10 }

        hwSiteDCDBLoad2LvdTime OBJECT-TYPE
            SYNTAX Integer32 (0..6000)
            MAX-ACCESS read-write
            STATUS current
            DESCRIPTION
                "Low-voltage power-off disconnected time, It can be configured by users, and its value is an integer (1). 
                Here, if lvd mode is time mode, value range defines between 0 to 6000, 
                unit: minutes(min). 
                If the value is 2147483647(0x7FFFFFFF), it indicates that the value is invalid.
                NOTE: Only the lvd in time power off mode, this parameter can be configured successfully."
            ::= { hwSiteDCDBSetEntry 11 }

        hwSiteDCDBLoad2LvdCapacity OBJECT-TYPE
            SYNTAX Integer32 (0..99)
            MAX-ACCESS read-write
            STATUS current
            DESCRIPTION
                "Power-off unit control the power off, when Remaining capacity percentage of the battery strings is below the calue. 
                Value range: 0 to 99, 
                unit: %,
                and the value is accurate to one decimal place (.1).  If the value is 2147483647(0x7FFFFFFF), it indicates that the value is invalid.
                NOTE: Only the lvd in capacity power off mode, this parameter can be configured successfully."
            ::= { hwSiteDCDBSetEntry 12 }

        hwSiteDCDBSetLLVD1PowerOffConsumption OBJECT-TYPE
            SYNTAX Unsigned32 (0..10000000)
            MAX-ACCESS read-write
            STATUS current
            DESCRIPTION
                "LLVD 1 power off consumption of DCDB. Value range: 0 to 10000000, unit: kWh, and the value is accurate to one decimal place (.01)."
            ::= { hwSiteDCDBSetEntry 14 }

        hwSiteDCDBSetLLVD2PowerOffConsumption OBJECT-TYPE
            SYNTAX Unsigned32 (0..10000000)
            MAX-ACCESS read-write
            STATUS current
            DESCRIPTION
                "LLVD 2 power off consumption of DCDB. Value range: 0 to 10000000, unit: kWh, and the value is accurate to one decimal place (.01)."
            ::= { hwSiteDCDBSetEntry 15 }

        hwSiteDCDBReset OBJECT-TYPE
            SYNTAX INTEGER
                {
                reset(1),
                unknown(255)
                }
            MAX-ACCESS read-write
            STATUS current
            DESCRIPTION
                "Board reset of DCDB, It is an enumeration type: 
                If the enumeration value is 2, it indicates that the lanch of the reset process;
                If the enumeration value of the node is 255, it indicates that the board reset the unknown of the DCDB. "
            ::= { hwSiteDCDBSetEntry 16 }

        hwSiteDCDBLoadOffAlmDelayTime OBJECT-TYPE
            SYNTAX Unsigned32 (0..4294967295)
            MAX-ACCESS read-write
            STATUS current
            DESCRIPTION
                "Load off alarm delay time of DCDB. Value range: 0 to 4294967295, unit: s, and the value is accurate to one decimal place (1.)."
            ::= { hwSiteDCDBSetEntry 17 }

        hwSiteDCDBDinLLVD1Enable OBJECT-TYPE
            SYNTAX INTEGER
                {
                disable(1),
                enable(2),
                unknown(255)
                }
            MAX-ACCESS read-write
            STATUS current
            DESCRIPTION
                "DIN for LLVD 1 enable of DCDB, It is an enumeration type: 
                If the enumeration value is 1, it indicates that the DIN for LLVD1 disable;
                If the enumeration value is 2, it indicates that the DIN for LLVD1 enable;"
            ::= { hwSiteDCDBSetEntry 18 }

        hwSiteDCDBDinLLVD1Index OBJECT-TYPE
            SYNTAX INTEGER
                {
                null(1),
                din1(2),
                din2(3),
                din3(4),
                din4(5),
                din5(6),
                din6(7),
                unknown(255)
                }
            MAX-ACCESS read-write
            STATUS current
            DESCRIPTION
                "LLVD 1 index of DCDB, It is an enumeration type: 
                If the enumeration value is 1, it indicates that no LLVD 1;
                If the enumeration value is 2, it indicates that LLVD 1 connect to DIN1;
                If the enumeration value is 3, it indicates that LLVD 1 connect to DIN2;
                If the enumeration value is 4, it indicates that LLVD 1 connect to DIN3;
                If the enumeration value is 5, it indicates that LLVD 1 connect to DIN4;
                If the enumeration value is 6, it indicates that LLVD 1 connect to DIN5;
                If the enumeration value is 7, it indicates that LLVD 1 connect to DIN6;"
            ::= { hwSiteDCDBSetEntry 19 }

        hwSiteDCDBDinLLVD1Condition OBJECT-TYPE
            SYNTAX INTEGER
                {
                open(1),
                close(2),
                unknown(255)
                }
            MAX-ACCESS read-write
            STATUS current
            DESCRIPTION
                "DIN condition for LLVD 1 of DCDB, It is an enumeration type: 
                If the enumeration value is 1, it indicates that the DIN open;
                If the enumeration value is 2, it indicates that the DIN close;"
            ::= { hwSiteDCDBSetEntry 20 }

        hwSiteDCDBDinLLVD1Delay OBJECT-TYPE
            SYNTAX Unsigned32 (0..600)
            MAX-ACCESS read-write
            STATUS current
            DESCRIPTION
                "DIN LLVD1 Delay time of DCDB. Value range: 0 to 600, unit: min, and the value is accurate to one decimal place (1.)."
            ::= { hwSiteDCDBSetEntry 21 }

        hwSiteDCDBDinLLVD2Enable OBJECT-TYPE
            SYNTAX INTEGER
                {
                disable(1),
                enable(2),
                unknown(255)
                }
            MAX-ACCESS read-write
            STATUS current
            DESCRIPTION
                "DIN for LLVD 2 enable of DCDB, It is an enumeration type: 
                If the enumeration value is 1, it indicates that the DIN for LLVD2 disable;
                If the enumeration value is 2, it indicates that the DIN for LLVD2 enable;"
            ::= { hwSiteDCDBSetEntry 22 }

        hwSiteDCDBDinLLVD2Index OBJECT-TYPE
            SYNTAX INTEGER
                {
                null(1),
                din1(2),
                din2(3),
                din3(4),
                din4(5),
                din5(6),
                din6(7),
                unknown(255)
                }
            MAX-ACCESS read-write
            STATUS current
            DESCRIPTION
                "LLVD 2 index of DCDB, It is an enumeration type: 
                If the enumeration value is 1, it indicates that no LLVD 2;
                If the enumeration value is 2, it indicates that LLVD 2 connect to DIN1;
                If the enumeration value is 3, it indicates that LLVD 2 connect to DIN2;
                If the enumeration value is 4, it indicates that LLVD 2 connect to DIN3;
                If the enumeration value is 5, it indicates that LLVD 1 connect to DIN4;
                If the enumeration value is 6, it indicates that LLVD 1 connect to DIN5;
                If the enumeration value is 7, it indicates that LLVD 1 connect to DIN6;"
            ::= { hwSiteDCDBSetEntry 23 }

        hwSiteDCDBDinLLVD2Condition OBJECT-TYPE
            SYNTAX INTEGER
                {
                open(1),
                close(2),
                unknown(255)
                }
            MAX-ACCESS read-write
            STATUS current
            DESCRIPTION
                "DIN condition for LLVD 2 of DCDB, It is an enumeration type: 
                If the enumeration value is 1, it indicates that the DIN open;
                If the enumeration value is 2, it indicates that the DIN close;"
            ::= { hwSiteDCDBSetEntry 24 }

        hwSiteDCDBDinLLVD2Delay OBJECT-TYPE
            SYNTAX Unsigned32 (0..600)
            MAX-ACCESS read-write
            STATUS current
            DESCRIPTION
                "DIN LLVD2 Delay time of DCDB. Value range: 0 to 600, unit: min, and the value is accurate to one decimal place (1.)."
            ::= { hwSiteDCDBSetEntry 25 }

        hwSiteDCDBSetLoad1UserConfig OBJECT-TYPE
            SYNTAX INTEGER
                {
                null(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "Set load 1 user config of DCDB, It is an enumeration type."
            ::= { hwSiteDCDBSetEntry 26 }

        hwSiteDCDBSetLoad2UserConfig OBJECT-TYPE
            SYNTAX INTEGER
                {
                null(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "Set load 2 user config of DCDB, It is an enumeration type."
            ::= { hwSiteDCDBSetEntry 27 }

        hwSiteDCDBSetPowerSupplySource OBJECT-TYPE
            SYNTAX INTEGER
                {
                busbar(1),
                llvd1(2),
                llvd2(3),
                llvd3(4),
                llvd4(5),
                llvd5(6),
                llvd6(7),
                llvd7(8),
                llvd8(9),
                llvd9(10),
                llvd10(11),
                powerCascadingPort(12),
                unknown(255)
                }
            MAX-ACCESS read-write
            STATUS current
            DESCRIPTION
                "Set power supply source of DCDB, It is an enumeration type."
            ::= { hwSiteDCDBSetEntry 28 }

        hwSiteDCDBSetLLVD1EnableForPeakShaving OBJECT-TYPE
            SYNTAX INTEGER
                {
                disable(1),
                enable(2),
                unknown(255)
                }
            MAX-ACCESS read-write
            STATUS current
            DESCRIPTION
                "LLVD1 enable for peak shaving of DCDB, It is an enumeration type: 
                If the enumeration value is 1, it indicates that the peak shaving enable;
                If the enumeration value is 2, it indicates that the peak shaving disable;"
            ::= { hwSiteDCDBSetEntry 29 }

        hwSiteDCDBSetLLVD2EnableForPeakShaving OBJECT-TYPE
            SYNTAX INTEGER
                {
                disable(1),
                enable(2),
                unknown(255)
                }
            MAX-ACCESS read-write
            STATUS current
            DESCRIPTION
                "LLVD2 enable for peak shaving of DCDB, It is an enumeration type: 
                If the enumeration value is 1, it indicates that the peak shaving disable;
                If the enumeration value is 2, it indicates that the peak shaving enable;"
            ::= { hwSiteDCDBSetEntry 30 }

        hwSiteDCDBSetLLVD1TimingOnOffEnable OBJECT-TYPE
            SYNTAX INTEGER
                {
                disable(1),
                enable(2),
                unknown(255)
                }
            MAX-ACCESS read-write
            STATUS current
            DESCRIPTION
                "LLVD1 Timing OnOff enable of DCDB, It is an enumeration type: 
                If the enumeration value is 1, it indicates that the Timing OnOff disable;
                If the enumeration value is 2, it indicates that the Timing OnOff enable;"
            ::= { hwSiteDCDBSetEntry 31 }

        hwSiteDCDBSetLLVD1TimingOnOffStartTime1 OBJECT-TYPE
            SYNTAX OCTET STRING (SIZE (0..60))
            MAX-ACCESS read-write
            STATUS current
            DESCRIPTION
                "Set LLVD1 Timing OnOff start time 1"
            ::= { hwSiteDCDBSetEntry 32 }

        hwSiteDCDBSetLLVD1TimedDuration1 OBJECT-TYPE
            SYNTAX Unsigned32 (0..1440)
            MAX-ACCESS read-write
            STATUS current
            DESCRIPTION
                "Set LLVD1 Timing duration 1"
            ::= { hwSiteDCDBSetEntry 33 }

        hwSiteDCDBSetLLVD1TimingOnOffStartTime2 OBJECT-TYPE
            SYNTAX OCTET STRING (SIZE (0..60))
            MAX-ACCESS read-write
            STATUS current
            DESCRIPTION
                "Set LLVD1 Timing OnOff start time 2"
            ::= { hwSiteDCDBSetEntry 34 }

        hwSiteDCDBSetLLVD1TimedDuration2 OBJECT-TYPE
            SYNTAX Unsigned32 (0..1440)
            MAX-ACCESS read-write
            STATUS current
            DESCRIPTION
                "Set LLVD1 Timing duration 2"
            ::= { hwSiteDCDBSetEntry 35 }

        hwSiteDCDBSetLLVD1TimingOnOffStartTime3 OBJECT-TYPE
            SYNTAX OCTET STRING (SIZE (0..60))
            MAX-ACCESS read-write
            STATUS current
            DESCRIPTION
                "Set LLVD1 Timing OnOff start time 3"
            ::= { hwSiteDCDBSetEntry 36 }

        hwSiteDCDBSetLLVD1TimedDuration3 OBJECT-TYPE
            SYNTAX Unsigned32 (0..1440)
            MAX-ACCESS read-write
            STATUS current
            DESCRIPTION
                "Set LLVD1 Timing duration 3"
            ::= { hwSiteDCDBSetEntry 37 }

        hwSiteDCDBSetLLVD1TimingOnOffStartTime4 OBJECT-TYPE
            SYNTAX OCTET STRING (SIZE (0..60))
            MAX-ACCESS read-write
            STATUS current
            DESCRIPTION
                "Set LLVD1 Timing OnOff start time 4"
            ::= { hwSiteDCDBSetEntry 38 }

        hwSiteDCDBSetLLVD1TimedDuration4 OBJECT-TYPE
            SYNTAX Unsigned32 (0..1440)
            MAX-ACCESS read-write
            STATUS current
            DESCRIPTION
                "Set LLVD1 Timing duration 4"
            ::= { hwSiteDCDBSetEntry 39 }

        hwSiteDCDBSetLLVD1TimingOnOffStartTime5 OBJECT-TYPE
            SYNTAX OCTET STRING (SIZE (0..60))
            MAX-ACCESS read-write
            STATUS current
            DESCRIPTION
                "Set LLVD1 Timing OnOff start time 5"
            ::= { hwSiteDCDBSetEntry 40 }

        hwSiteDCDBSetLLVD1TimedDuration5 OBJECT-TYPE
            SYNTAX Unsigned32 (0..1440)
            MAX-ACCESS read-write
            STATUS current
            DESCRIPTION
                "Set LLVD1 Timing duration 5"
            ::= { hwSiteDCDBSetEntry 41 }

        hwSiteDCDBSetLLVD2TimingOnOffEnable OBJECT-TYPE
            SYNTAX INTEGER
                {
                disable(1),
                enable(2),
                unknown(255)
                }
            MAX-ACCESS read-write
            STATUS current
            DESCRIPTION
                "LLVD2 Timing OnOff enable of DCDB, It is an enumeration type: 
                If the enumeration value is 1, it indicates that the Timing OnOff disable;
                If the enumeration value is 2, it indicates that the Timing OnOff enable;"
            ::= { hwSiteDCDBSetEntry 42 }

        hwSiteDCDBSetLLVD2TimingOnOffStartTime1 OBJECT-TYPE
            SYNTAX OCTET STRING (SIZE (0..60))
            MAX-ACCESS read-write
            STATUS current
            DESCRIPTION
                "Set LLVD2 Timing OnOff start time 1"
            ::= { hwSiteDCDBSetEntry 43 }

        hwSiteDCDBSetLLVD2TimedDuration1 OBJECT-TYPE
            SYNTAX Unsigned32 (0..1440)
            MAX-ACCESS read-write
            STATUS current
            DESCRIPTION
                "Set LLVD2 Timing duration 1"
            ::= { hwSiteDCDBSetEntry 44 }

        hwSiteDCDBSetLLVD2TimingOnOffStartTime2 OBJECT-TYPE
            SYNTAX OCTET STRING (SIZE (0..60))
            MAX-ACCESS read-write
            STATUS current
            DESCRIPTION
                "Set LLVD2 Timing OnOff start time 2"
            ::= { hwSiteDCDBSetEntry 45 }

        hwSiteDCDBSetLLVD2TimedDuration2 OBJECT-TYPE
            SYNTAX Unsigned32 (0..1440)
            MAX-ACCESS read-write
            STATUS current
            DESCRIPTION
                "Set LLVD2 Timing duration 2"
            ::= { hwSiteDCDBSetEntry 46 }

        hwSiteDCDBSetLLVD2TimingOnOffStartTime3 OBJECT-TYPE
            SYNTAX OCTET STRING (SIZE (0..60))
            MAX-ACCESS read-write
            STATUS current
            DESCRIPTION
                "Set LLVD2 Timing OnOff start time 3"
            ::= { hwSiteDCDBSetEntry 47 }

        hwSiteDCDBSetLLVD2TimedDuration3 OBJECT-TYPE
            SYNTAX Unsigned32 (0..1440)
            MAX-ACCESS read-write
            STATUS current
            DESCRIPTION
                "Set LLVD2 Timing duration 3"
            ::= { hwSiteDCDBSetEntry 48 }

        hwSiteDCDBSetLLVD2TimingOnOffStartTime4 OBJECT-TYPE
            SYNTAX OCTET STRING (SIZE (0..60))
            MAX-ACCESS read-write
            STATUS current
            DESCRIPTION
                "Set LLVD2 Timing OnOff start time 4"
            ::= { hwSiteDCDBSetEntry 49 }

        hwSiteDCDBSetLLVD2TimedDuration4 OBJECT-TYPE
            SYNTAX Unsigned32 (0..1440)
            MAX-ACCESS read-write
            STATUS current
            DESCRIPTION
                "Set LLVD2 Timing duration 4"
            ::= { hwSiteDCDBSetEntry 50 }

        hwSiteDCDBSetLLVD2TimingOnOffStartTime5 OBJECT-TYPE
            SYNTAX OCTET STRING (SIZE (0..60))
            MAX-ACCESS read-write
            STATUS current
            DESCRIPTION
                "Set LLVD2 Timing OnOff start time 5"
            ::= { hwSiteDCDBSetEntry 51 }

        hwSiteDCDBSetLLVD2TimedDuration5 OBJECT-TYPE
            SYNTAX Unsigned32 (0..1440)
            MAX-ACCESS read-write
            STATUS current
            DESCRIPTION
                "Set LLVD2 Timing duration 5"
            ::= { hwSiteDCDBSetEntry 52 }

        hwSiteDCDBSetLLVD1ExemptPeriodOnOffEnable OBJECT-TYPE
            SYNTAX INTEGER
                {
                disable(1),
                enable(2),
                unknown(255)
                }
            MAX-ACCESS read-write
            STATUS current
            DESCRIPTION
                "LLVD1 exempt period onoff enable of DCDB, It is an enumeration type: 
                If the enumeration value is 1, it indicates that the Timing OnOff disable;
                If the enumeration value is 2, it indicates that the Timing OnOff enable;"
            ::= { hwSiteDCDBSetEntry 53 }

        hwSiteDCDBSetLLVD1ExemptPeriodOnOffStartTime1 OBJECT-TYPE
            SYNTAX OCTET STRING (SIZE (0..60))
            MAX-ACCESS read-write
            STATUS current
            DESCRIPTION
                "Set LLVD1 exempt period start time 1"
            ::= { hwSiteDCDBSetEntry 54 }

        hwSiteDCDBSetLLVD1ExemptDuration1 OBJECT-TYPE
            SYNTAX Unsigned32 (0..1440)
            MAX-ACCESS read-write
            STATUS current
            DESCRIPTION
                "Set LLVD1 exempt duration 1"
            ::= { hwSiteDCDBSetEntry 55 }

        hwSiteDCDBSetLLVD1ExemptPeriodOnOffStartTime2 OBJECT-TYPE
            SYNTAX OCTET STRING (SIZE (0..60))
            MAX-ACCESS read-write
            STATUS current
            DESCRIPTION
                "Set LLVD1 exempt period start time 2"
            ::= { hwSiteDCDBSetEntry 56 }

        hwSiteDCDBSetLLVD1ExemptDuration2 OBJECT-TYPE
            SYNTAX Unsigned32 (0..1440)
            MAX-ACCESS read-write
            STATUS current
            DESCRIPTION
                "Set LLVD1 exempt duration 2"
            ::= { hwSiteDCDBSetEntry 57 }

        hwSiteDCDBSetLLVD1ExemptPeriodOnOffStartTime3 OBJECT-TYPE
            SYNTAX OCTET STRING (SIZE (0..60))
            MAX-ACCESS read-write
            STATUS current
            DESCRIPTION
                "Set LLVD1 exempt period start time 3"
            ::= { hwSiteDCDBSetEntry 58 }

        hwSiteDCDBSetLLVD1ExemptDuration3 OBJECT-TYPE
            SYNTAX Unsigned32 (0..1440)
            MAX-ACCESS read-write
            STATUS current
            DESCRIPTION
                "Set LLVD1 exempt duration 3"
            ::= { hwSiteDCDBSetEntry 59 }

        hwSiteDCDBSetLLVD1ExemptPeriodOnOffStartTime4 OBJECT-TYPE
            SYNTAX OCTET STRING (SIZE (0..60))
            MAX-ACCESS read-write
            STATUS current
            DESCRIPTION
                "Set LLVD1 exempt period start time 4"
            ::= { hwSiteDCDBSetEntry 60 }

        hwSiteDCDBSetLLVD1ExemptDuration4 OBJECT-TYPE
            SYNTAX Unsigned32 (0..1440)
            MAX-ACCESS read-write
            STATUS current
            DESCRIPTION
                "Set LLVD1 exempt duration 4"
            ::= { hwSiteDCDBSetEntry 61 }

        hwSiteDCDBSetLLVD1ExemptPeriodOnOffStartTime5 OBJECT-TYPE
            SYNTAX OCTET STRING (SIZE (0..60))
            MAX-ACCESS read-write
            STATUS current
            DESCRIPTION
                "Set LLVD1 exempt period start time 5"
            ::= { hwSiteDCDBSetEntry 62 }

        hwSiteDCDBSetLLVD1ExemptDuration5 OBJECT-TYPE
            SYNTAX Unsigned32 (0..1440)
            MAX-ACCESS read-write
            STATUS current
            DESCRIPTION
                "Set LLVD1 exempt duration 5"
            ::= { hwSiteDCDBSetEntry 63 }

        hwSiteDCDBSetLLVD2ExemptPeriodOnOffEnable OBJECT-TYPE
            SYNTAX INTEGER
                {
                disable(1),
                enable(2),
                unknown(255)
                }
            MAX-ACCESS read-write
            STATUS current
            DESCRIPTION
                "LLVD2 exempt period onoff enable of DCDB, It is an enumeration type: 
                If the enumeration value is 1, it indicates that the Timing OnOff disable;
                If the enumeration value is 2, it indicates that the Timing OnOff enable;"
            ::= { hwSiteDCDBSetEntry 64 }

        hwSiteDCDBSetLLVD2ExemptPeriodOnOffStartTime1 OBJECT-TYPE
            SYNTAX OCTET STRING (SIZE (0..60))
            MAX-ACCESS read-write
            STATUS current
            DESCRIPTION
                "Set LLVD2 exempt period start time 1"
            ::= { hwSiteDCDBSetEntry 65 }

        hwSiteDCDBSetLLVD2ExemptDuration1 OBJECT-TYPE
            SYNTAX Unsigned32 (0..1440)
            MAX-ACCESS read-write
            STATUS current
            DESCRIPTION
                "Set LLVD2 exempt duration 1"
            ::= { hwSiteDCDBSetEntry 66 }

        hwSiteDCDBSetLLVD2ExemptPeriodOnOffStartTime2 OBJECT-TYPE
            SYNTAX OCTET STRING (SIZE (0..60))
            MAX-ACCESS read-write
            STATUS current
            DESCRIPTION
                "Set LLVD2 exempt period start time 2"
            ::= { hwSiteDCDBSetEntry 67 }

        hwSiteDCDBSetLLVD2ExemptDuration2 OBJECT-TYPE
            SYNTAX Unsigned32 (0..1440)
            MAX-ACCESS read-write
            STATUS current
            DESCRIPTION
                "Set LLVD2 exempt duration 2"
            ::= { hwSiteDCDBSetEntry 68 }

        hwSiteDCDBSetLLVD2ExemptPeriodOnOffStartTime3 OBJECT-TYPE
            SYNTAX OCTET STRING (SIZE (0..60))
            MAX-ACCESS read-write
            STATUS current
            DESCRIPTION
                "Set LLVD2 exempt period start time 3"
            ::= { hwSiteDCDBSetEntry 69 }

        hwSiteDCDBSetLLVD2ExemptDuration3 OBJECT-TYPE
            SYNTAX Unsigned32 (0..1440)
            MAX-ACCESS read-write
            STATUS current
            DESCRIPTION
                "Set LLVD2 exempt duration 3"
            ::= { hwSiteDCDBSetEntry 70 }

        hwSiteDCDBSetLLVD2ExemptPeriodOnOffStartTime4 OBJECT-TYPE
            SYNTAX OCTET STRING (SIZE (0..60))
            MAX-ACCESS read-write
            STATUS current
            DESCRIPTION
                "Set LLVD2 exempt period start time 4"
            ::= { hwSiteDCDBSetEntry 71 }

        hwSiteDCDBSetLLVD2ExemptDuration4 OBJECT-TYPE
            SYNTAX Unsigned32 (0..1440)
            MAX-ACCESS read-write
            STATUS current
            DESCRIPTION
                "Set LLVD2 exempt duration 4"
            ::= { hwSiteDCDBSetEntry 72 }

        hwSiteDCDBSetLLVD2ExemptPeriodOnOffStartTime5 OBJECT-TYPE
            SYNTAX OCTET STRING (SIZE (0..60))
            MAX-ACCESS read-write
            STATUS current
            DESCRIPTION
                "Set LLVD2 exempt period start time 5"
            ::= { hwSiteDCDBSetEntry 73 }

        hwSiteDCDBSetLLVD2ExemptDuration5 OBJECT-TYPE
            SYNTAX Unsigned32 (0..1440)
            MAX-ACCESS read-write
            STATUS current
            DESCRIPTION
                "Set LLVD2 exempt duration 5"
            ::= { hwSiteDCDBSetEntry 74 }

        hwSiteDCDBSetLLVD1DGOff OBJECT-TYPE
            SYNTAX INTEGER
                {
                disable(1),
                enable(2),
                unknown(255)
                }
            MAX-ACCESS read-write
            STATUS current
            DESCRIPTION
                "DCDB DG service for LLVD1"
            ::= { hwSiteDCDBSetEntry 75 }

        hwSiteDCDBSetLLVD2DGOff OBJECT-TYPE
            SYNTAX INTEGER
                {
                disable(1),
                enable(2),
                unknown(255)
                }
            MAX-ACCESS read-write
            STATUS current
            DESCRIPTION
                "DCDB DG service for LLVD2"
            ::= { hwSiteDCDBSetEntry 76 }

        hwSiteAts OBJECT IDENTIFIER ::= { hwSiteMonitorMIBObjects 33 }

        hwAtsSampTable OBJECT-TYPE
            SYNTAX SEQUENCE OF HwAtsSampEntry
            MAX-ACCESS not-accessible
             STATUS current
             DESCRIPTION
                ""
            ::= { hwSiteAts 1 }

        hwAtsSampEntry OBJECT-TYPE
                        SYNTAX HwAtsSampEntry
            MAX-ACCESS not-accessible
             STATUS current
             DESCRIPTION
                ""
            INDEX { hwAtsIndex }
            ::= { hwAtsSampTable 1 }

        HwAtsSampEntry            ::= SEQUENCE {
                hwAtsIndex
                    Unsigned32,
                hwAtsEquipId
                    Unsigned32,
                hwAtsEquipName
                    OCTET STRING
            }

        hwAtsIndex OBJECT-TYPE
            SYNTAX Unsigned32 (0..256)
            MAX-ACCESS read-only
            STATUS current
            DESCRIPTION
                "Table index of the running ATS modules"
            ::= { hwAtsSampEntry 1 }

        hwAtsEquipId OBJECT-TYPE
            SYNTAX Unsigned32
            MAX-ACCESS read-only
            STATUS current
            DESCRIPTION
                "ATS module ID. "
            ::= { hwAtsSampEntry 2 }

        hwAtsEquipName OBJECT-TYPE
            SYNTAX OCTET STRING (SIZE (0..63))
            MAX-ACCESS read-only
            STATUS current
            DESCRIPTION
                "Device name of the ATS module"
            ::= { hwAtsSampEntry 3 }

        hwLiBatteryCabinet OBJECT IDENTIFIER ::= { hwSiteMonitorMIBObjects 34 }

        hwLiBatteryCabinetInfoTable OBJECT-TYPE
            SYNTAX SEQUENCE OF HwLiBatteryCabinetInfoEntry
            MAX-ACCESS not-accessible
             STATUS current
             DESCRIPTION
                "/"
            ::= { hwLiBatteryCabinet 1 }

        hwLiBatteryCabinetInfoEntry OBJECT-TYPE
                        SYNTAX HwLiBatteryCabinetInfoEntry
            MAX-ACCESS not-accessible
             STATUS current
             DESCRIPTION
                "/"
            INDEX { hwLiBatteryCabinetIndex }
            ::= { hwLiBatteryCabinetInfoTable 1 }

        HwLiBatteryCabinetInfoEntry            ::= SEQUENCE {
                hwLiBatteryCabinetIndex
                    Unsigned32,
                hwLiBatteryCabinetEquipId
                    Unsigned32,
                hwLiBatteryCabinetEquipName
                    OCTET STRING,
                hwLiBatteryCabinetBatteryTotalCurrent
                    Integer32,
                hwLiBatteryCabinetBMUTotalQuantity
                    Unsigned32,
                hwLiBatteryCabinetBMUOnlineQuantity
                    Unsigned32,
                hwLiBatteryCabinetBMUOfflineQuantity
                    Unsigned32
            }

        hwLiBatteryCabinetIndex OBJECT-TYPE
            SYNTAX Unsigned32
            MAX-ACCESS read-only
            STATUS current
            DESCRIPTION
                "The Li Battery Cabinet Index."
            ::= { hwLiBatteryCabinetInfoEntry 1 }

        hwLiBatteryCabinetEquipId OBJECT-TYPE
            SYNTAX Unsigned32
            MAX-ACCESS read-only
            STATUS current
            DESCRIPTION
                "The Li Battery Cabinet equip ID no."
            ::= { hwLiBatteryCabinetInfoEntry 2 }

        hwLiBatteryCabinetEquipName OBJECT-TYPE
            SYNTAX OCTET STRING (SIZE (0..63))
            MAX-ACCESS read-only
            STATUS current
            DESCRIPTION
                "The Li Battery Cabinet equip name."
            ::= { hwLiBatteryCabinetInfoEntry 3 }

        hwLiBatteryCabinetBatteryTotalCurrent OBJECT-TYPE
            SYNTAX Integer32 ( -640000..640000)
            MAX-ACCESS read-only
            STATUS current
            DESCRIPTION
                "Li battery cabinet total current: -64000 to 64000, 
                unit: A, 
                and the value is one decimal space (.1). If the value is 2147483647(0x7FFFFFFF), it indicates that the value is invalid."
            ::= { hwLiBatteryCabinetInfoEntry 4 }

        hwLiBatteryCabinetBMUTotalQuantity OBJECT-TYPE
            SYNTAX Unsigned32 (0..32)
            MAX-ACCESS read-only
            STATUS current
            DESCRIPTION
                "The Total Li battary number of the LiBattery cabinet."
            ::= { hwLiBatteryCabinetInfoEntry 5 }

        hwLiBatteryCabinetBMUOnlineQuantity OBJECT-TYPE
            SYNTAX Unsigned32 (0..32)
            MAX-ACCESS read-only
            STATUS current
            DESCRIPTION
                "The  online Li battary number of the LiBattery cabinet."
            ::= { hwLiBatteryCabinetInfoEntry 6 }

        hwLiBatteryCabinetBMUOfflineQuantity OBJECT-TYPE
            SYNTAX Unsigned32 (0..32)
            MAX-ACCESS read-only
            STATUS current
            DESCRIPTION
                "The  offline Li battary number of the LiBattery cabinet."
            ::= { hwLiBatteryCabinetInfoEntry 7 }

        hwDcCabinet OBJECT IDENTIFIER ::= { hwSiteMonitorMIBObjects 35 }

        hwDcCabinetInfoTable OBJECT-TYPE
            SYNTAX SEQUENCE OF HwDcCabinetInfoEntry
            MAX-ACCESS not-accessible
             STATUS current
             DESCRIPTION
                "/"
            ::= { hwDcCabinet 1 }

        hwDcCabinetInfoEntry OBJECT-TYPE
                        SYNTAX HwDcCabinetInfoEntry
            MAX-ACCESS not-accessible
             STATUS current
             DESCRIPTION
                "/"
            INDEX { hwDcCabinetIndex }
            ::= { hwDcCabinetInfoTable 1 }

        HwDcCabinetInfoEntry            ::= SEQUENCE {
                hwDcCabinetIndex
                    Unsigned32,
                hwDcCabinetEquipId
                    Unsigned32,
                hwDcCabinetEquipName
                    OCTET STRING,
                hwDcCabinetDcVoltage
                    Unsigned32,
                hwDcCabinetIndoorTemperature
                    Integer32,
                hwDcCabinetTotalLoadCurrent
                    Unsigned32,
                hwDcCabinetCabinetModel
                    OCTET STRING,
                hwDcCabinetBatteryCurrent
                    Integer32,
                hwDcCabinetBatteryTemperature1
                    Integer32,
                hwDcCabinetBatteryTemperature2
                    Integer32,
                hwDcCabinetBatteryTemperature3
                    Integer32,
                hwDcCabinetBatteryTemperature4
                    Integer32,
                hwDcCabinetBatteryTemperature5
                    Integer32,
                hwDcCabinetBatteryTemperature6
                    Integer32,
                hwDcCabinetBatteryTemperature7
                    Integer32,
                hwDcCabinetBatteryTemperature8
                    Integer32,
                hwDcCabinetBatteryTemperature9
                    Integer32,
                hwDcCabinetBatteryTemperature10
                    Integer32,
                hwDcCabinetTotalLoadPower
                    Unsigned32,
                hwDcCabinetTotalLoadEnergyConsumption
                    Unsigned32
            }

        hwDcCabinetIndex OBJECT-TYPE
            SYNTAX Unsigned32
            MAX-ACCESS read-only
            STATUS current
            DESCRIPTION
                "The Dc Cabinet Index."
            ::= { hwDcCabinetInfoEntry 1 }

        hwDcCabinetEquipId OBJECT-TYPE
            SYNTAX Unsigned32
            MAX-ACCESS read-only
            STATUS current
            DESCRIPTION
                "The Dc Cabinet equip ID no."
            ::= { hwDcCabinetInfoEntry 2 }

        hwDcCabinetEquipName OBJECT-TYPE
            SYNTAX OCTET STRING (SIZE (0..63))
            MAX-ACCESS read-only
            STATUS current
            DESCRIPTION
                "The Dc Cabinet equip name."
            ::= { hwDcCabinetInfoEntry 3 }

        hwDcCabinetDcVoltage OBJECT-TYPE
            SYNTAX Unsigned32 (0..1000)
            MAX-ACCESS read-only
            STATUS current
            DESCRIPTION
                "Bus voltage  of the Dc cabinet. 
                Its value range: 0 to 100, 
                unit: V, 
                and the value is accurate to one decimal space (.1).  
                If the value is 2147483647(0x7FFFFFFF), it indicates that the value is invalid."
            ::= { hwDcCabinetInfoEntry 4 }

        hwDcCabinetIndoorTemperature OBJECT-TYPE
            SYNTAX Integer32 ( -40..80)
            MAX-ACCESS read-only
            STATUS current
            DESCRIPTION
                "The environment  temperature of Dc cabinet. It is a parameter collected in real time. 
                Value range: -40 to 80,
                unit: centigrade (degC), 
                and the value is an integer .
                If the value is 2147483647(0x7FFFFFFF), it indicates that battery temperature sensor is not configured."
            ::= { hwDcCabinetInfoEntry 5 }

        hwDcCabinetTotalLoadCurrent OBJECT-TYPE
            SYNTAX Unsigned32 (0..500000)
            MAX-ACCESS read-only
            STATUS current
            DESCRIPTION
                "Load current: 0 to 50000, 
                unit: A, 
                and the value is one decimal space (.1). If the value is 2147483647(0x7FFFFFFF), it indicates that the value is invalid."
            ::= { hwDcCabinetInfoEntry 6 }

        hwDcCabinetCabinetModel OBJECT-TYPE
            SYNTAX OCTET STRING
            MAX-ACCESS read-only
            STATUS current
            DESCRIPTION
                "System type name of the Dc Cabinet."
            ::= { hwDcCabinetInfoEntry 7 }

        hwDcCabinetBatteryCurrent OBJECT-TYPE
            SYNTAX Integer32 ( -500000..500000)
            MAX-ACCESS read-only
            STATUS current
            DESCRIPTION
                "DC cabinet Batt current: -50000 to 50000, 
                unit: A, 
                and the value is one decimal space (.1). If the value is 2147483647(0x7FFFFFFF), it indicates that the value is invalid."
            ::= { hwDcCabinetInfoEntry 8 }

        hwDcCabinetBatteryTemperature1 OBJECT-TYPE
            SYNTAX Integer32 ( -40..80)
            MAX-ACCESS read-only
            STATUS current
            DESCRIPTION
                "Battary temperature1. It is a battary parameter collected in real time. 
                Value range: -40 to 80, 
                unit: centigrade (degC), 
                and the value is an integer .
                If the value is 2147483647(0x7FFFFFFF), it indicates that battery temperature sensor is not configured."
            ::= { hwDcCabinetInfoEntry 9 }

        hwDcCabinetBatteryTemperature2 OBJECT-TYPE
            SYNTAX Integer32 ( -40..80)
            MAX-ACCESS read-only
            STATUS current
            DESCRIPTION
                "Battary temperature2. It is a battary parameter collected in real time. 
                Value range: -40 to 80, 
                unit: centigrade (degC), 
                and the value is an integer .
                If the value is 2147483647(0x7FFFFFFF), it indicates that battery temperature sensor is not configured."
            ::= { hwDcCabinetInfoEntry 10 }

        hwDcCabinetBatteryTemperature3 OBJECT-TYPE
            SYNTAX Integer32 ( -40..80)
            MAX-ACCESS read-only
            STATUS current
            DESCRIPTION
                "Battary temperature3. It is a battary parameter collected in real time. 
                Value range: -40 to 80, 
                unit: centigrade (degC), 
                and the value is an integer .
                If the value is 2147483647(0x7FFFFFFF), it indicates that battery temperature sensor is not configured."
            ::= { hwDcCabinetInfoEntry 11 }

        hwDcCabinetBatteryTemperature4 OBJECT-TYPE
            SYNTAX Integer32 ( -40..80)
            MAX-ACCESS read-only
            STATUS current
            DESCRIPTION
                "Battary temperature4. It is a battary parameter collected in real time. 
                Value range: -40 to 80, 
                unit: centigrade (degC), 
                and the value is an integer .
                If the value is 2147483647(0x7FFFFFFF), it indicates that battery temperature sensor is not configured."
            ::= { hwDcCabinetInfoEntry 12 }

        hwDcCabinetBatteryTemperature5 OBJECT-TYPE
            SYNTAX Integer32 ( -40..80)
            MAX-ACCESS read-only
            STATUS current
            DESCRIPTION
                "Battary temperature5. It is a battary parameter collected in real time. 
                Value range: -40 to 80, 
                unit: centigrade (degC), 
                and the value is an integer .
                If the value is 2147483647(0x7FFFFFFF), it indicates that battery temperature sensor is not configured."
            ::= { hwDcCabinetInfoEntry 13 }

        hwDcCabinetBatteryTemperature6 OBJECT-TYPE
            SYNTAX Integer32 ( -40..80)
            MAX-ACCESS read-only
            STATUS current
            DESCRIPTION
                "Battary temperature6. It is a battary parameter collected in real time. 
                Value range: -40 to 80, 
                unit: centigrade (degC), 
                and the value is an integer .
                If the value is 2147483647(0x7FFFFFFF), it indicates that battery temperature sensor is not configured."
            ::= { hwDcCabinetInfoEntry 14 }

        hwDcCabinetBatteryTemperature7 OBJECT-TYPE
            SYNTAX Integer32 ( -40..80)
            MAX-ACCESS read-only
            STATUS current
            DESCRIPTION
                "Battary7 temperature. It is a battary parameter collected in real time. 
                Value range: -40 to 80, 
                unit: centigrade (degC), 
                and the value is an integer .
                If the value is 2147483647(0x7FFFFFFF), it indicates that battery temperature sensor is not configured."
            ::= { hwDcCabinetInfoEntry 15 }

        hwDcCabinetBatteryTemperature8 OBJECT-TYPE
            SYNTAX Integer32 ( -40..80)
            MAX-ACCESS read-only
            STATUS current
            DESCRIPTION
                "Battary temperature8. It is a battary parameter collected in real time. 
                Value range: -40 to 80, 
                unit: centigrade (degC), 
                and the value is an integer .
                If the value is 2147483647(0x7FFFFFFF), it indicates that battery temperature sensor is not configured."
            ::= { hwDcCabinetInfoEntry 16 }

        hwDcCabinetBatteryTemperature9 OBJECT-TYPE
            SYNTAX Integer32 ( -40..80)
            MAX-ACCESS read-only
            STATUS current
            DESCRIPTION
                "Battary temperature9. It is a battary parameter collected in real time. 
                Value range: -40 to 80, 
                unit: centigrade (degC), 
                and the value is an integer .
                If the value is 2147483647(0x7FFFFFFF), it indicates that battery temperature sensor is not configured."
            ::= { hwDcCabinetInfoEntry 17 }

        hwDcCabinetBatteryTemperature10 OBJECT-TYPE
            SYNTAX Integer32 ( -40..80)
            MAX-ACCESS read-only
            STATUS current
            DESCRIPTION
                "Battary temperature10. It is a battary parameter collected in real time. 
                Value range: -40 to 80, 
                unit: centigrade (degC), 
                and the value is an integer .
                If the value is 2147483647(0x7FFFFFFF), it indicates that battery temperature sensor is not configured."
            ::= { hwDcCabinetInfoEntry 18 }

        hwDcCabinetTotalLoadPower OBJECT-TYPE
            SYNTAX Unsigned32 (0..1000000)
            MAX-ACCESS read-only
            STATUS current
            DESCRIPTION
                "Load power, 
                unit: kW, 
                and the value is one decimal space (.01). If the value is 2147483647(0x7FFFFFFF), it indicates that the value is invalid."
            ::= { hwDcCabinetInfoEntry 112 }

        hwDcCabinetTotalLoadEnergyConsumption OBJECT-TYPE
            SYNTAX Unsigned32 (0..1000000)
            MAX-ACCESS read-only
            STATUS current
            DESCRIPTION
                "Load Energy Consumption, 
                unit: kWh, 
                and the value is one decimal space (.01). If the value is 2147483647(0x7FFFFFFF), it indicates that the value is invalid."
            ::= { hwDcCabinetInfoEntry 113 }

        hwCombinedCabinet OBJECT IDENTIFIER ::= { hwSiteMonitorMIBObjects 36 }

        hwCombinedCabinetInfoTable OBJECT-TYPE
            SYNTAX SEQUENCE OF HwCombinedCabinetInfoEntry
            MAX-ACCESS not-accessible
             STATUS current
             DESCRIPTION
                "/"
            ::= { hwCombinedCabinet 1 }

        hwCombinedCabinetInfoEntry OBJECT-TYPE
                        SYNTAX HwCombinedCabinetInfoEntry
            MAX-ACCESS not-accessible
             STATUS current
             DESCRIPTION
                "/"
            INDEX { hwCombinedCabinetIndex }
            ::= { hwCombinedCabinetInfoTable 1 }

        HwCombinedCabinetInfoEntry            ::= SEQUENCE {
                hwCombinedCabinetIndex
                    Unsigned32,
                hwCombinedCabinetEquipId
                    Unsigned32,
                hwCombinedCabinetEquipName
                    OCTET STRING,
                hwCombinedCabinetDcVoltage
                    Unsigned32,
                hwCombinedCabinetBatteryTemperature1
                    Integer32,
                hwCombinedCabinetBatteryTemperature2
                    Integer32,
                hwCombinedCabinetTotalLoadCurrent
                    Unsigned32,
                hwCombinedCabinetTotalLoadPower
                    Unsigned32,
                hwCombinedCabinetTotalLoadEnergyConsumption
                    Unsigned32
            }

        hwCombinedCabinetIndex OBJECT-TYPE
            SYNTAX Unsigned32
            MAX-ACCESS read-only
            STATUS current
            DESCRIPTION
                "The Combined Cabinet Index."
            ::= { hwCombinedCabinetInfoEntry 1 }

        hwCombinedCabinetEquipId OBJECT-TYPE
            SYNTAX Unsigned32
            MAX-ACCESS read-only
            STATUS current
            DESCRIPTION
                "The Combined Cabinet equip ID no."
            ::= { hwCombinedCabinetInfoEntry 2 }

        hwCombinedCabinetEquipName OBJECT-TYPE
            SYNTAX OCTET STRING (SIZE (0..63))
            MAX-ACCESS read-only
            STATUS current
            DESCRIPTION
                "The Combined Cabinet equip name."
            ::= { hwCombinedCabinetInfoEntry 3 }

        hwCombinedCabinetDcVoltage OBJECT-TYPE
            SYNTAX Unsigned32 (0..1000)
            MAX-ACCESS read-only
            STATUS current
            DESCRIPTION
                "Dc voltage  of the Combined Cabinet. 
                Its value range: 0 to 100, 
                unit: V, 
                and the value is accurate to one decimal space (.1).  
                If the value is 2147483647(0x7FFFFFFF), it indicates that the value is invalid."
            ::= { hwCombinedCabinetInfoEntry 4 }

        hwCombinedCabinetBatteryTemperature1 OBJECT-TYPE
            SYNTAX Integer32 ( -300..200)
            MAX-ACCESS read-only
            STATUS current
            DESCRIPTION
                "Battary temperature1. It is a battary parameter collected in real time. 
                Value range: -300 to 200, 
                unit: centigrade (degC), 
                and the value is an integer .
                If the value is 2147483647(0x7FFFFFFF), it indicates that battery temperature sensor is not configured."
            ::= { hwCombinedCabinetInfoEntry 5 }

        hwCombinedCabinetBatteryTemperature2 OBJECT-TYPE
            SYNTAX Integer32 ( -300..200)
            MAX-ACCESS read-only
            STATUS current
            DESCRIPTION
                "Battary temperature2. It is a battary parameter collected in real time. 
                Value range: -300 to 200, 
                unit: centigrade (degC), 
                and the value is an integer .
                If the value is 2147483647(0x7FFFFFFF), it indicates that battery temperature sensor is not configured."
            ::= { hwCombinedCabinetInfoEntry 6 }

        hwCombinedCabinetTotalLoadCurrent OBJECT-TYPE
            SYNTAX Unsigned32 (0..100000)
            MAX-ACCESS read-only
            STATUS current
            DESCRIPTION
                "Load current, 
                unit: A, 
                and the value is one decimal space (.1). If the value is 2147483647(0x7FFFFFFF), it indicates that the value is invalid."
            ::= { hwCombinedCabinetInfoEntry 7 }

        hwCombinedCabinetTotalLoadPower OBJECT-TYPE
            SYNTAX Unsigned32 (0..100000)
            MAX-ACCESS read-only
            STATUS current
            DESCRIPTION
                "Load power, 
                unit: kW, 
                and the value is accurate to one decimal space (.1). If the value is 2147483647(0x7FFFFFFF), it indicates that the value is invalid."
            ::= { hwCombinedCabinetInfoEntry 8 }

        hwCombinedCabinetTotalLoadEnergyConsumption OBJECT-TYPE
            SYNTAX Unsigned32 (0..1000000)
            MAX-ACCESS read-only
            STATUS current
            DESCRIPTION
                "Load Energy Consumption, 
                unit: kWh, 
                and the value is one decimal space (.01). If the value is 2147483647(0x7FFFFFFF), it indicates that the value is invalid."
            ::= { hwCombinedCabinetInfoEntry 9 }

        hwRectifierCabinet OBJECT IDENTIFIER ::= { hwSiteMonitorMIBObjects 37 }

        hwRectifierCabinetInfoTable OBJECT-TYPE
            SYNTAX SEQUENCE OF HwRectifierCabinetInfoEntry
            MAX-ACCESS not-accessible
             STATUS current
             DESCRIPTION
                "/"
            ::= { hwRectifierCabinet 1 }

        hwRectifierCabinetInfoEntry OBJECT-TYPE
                        SYNTAX HwRectifierCabinetInfoEntry
            MAX-ACCESS not-accessible
             STATUS current
             DESCRIPTION
                "/"
            INDEX { hwRectifierCabinetIndex }
            ::= { hwRectifierCabinetInfoTable 1 }

        HwRectifierCabinetInfoEntry            ::= SEQUENCE {
                hwRectifierCabinetIndex
                    Unsigned32,
                hwRectifierCabinetEquipId
                    Unsigned32,
                hwRectifierCabinetEquipName
                    OCTET STRING,
                hwRectifierCabinetDcVoltage
                    Unsigned32,
                hwRectifierCabinetCabinetModel
                    OCTET STRING
            }

        hwRectifierCabinetIndex OBJECT-TYPE
            SYNTAX Unsigned32
            MAX-ACCESS read-only
            STATUS current
            DESCRIPTION
                "The Rectifier Cabinet Index."
            ::= { hwRectifierCabinetInfoEntry 1 }

        hwRectifierCabinetEquipId OBJECT-TYPE
            SYNTAX Unsigned32
            MAX-ACCESS read-only
            STATUS current
            DESCRIPTION
                "The Rectifier Cabinet equip ID no."
            ::= { hwRectifierCabinetInfoEntry 2 }

        hwRectifierCabinetEquipName OBJECT-TYPE
            SYNTAX OCTET STRING (SIZE (0..63))
            MAX-ACCESS read-only
            STATUS current
            DESCRIPTION
                "The Rectifier Cabinet equip name."
            ::= { hwRectifierCabinetInfoEntry 3 }

        hwRectifierCabinetDcVoltage OBJECT-TYPE
            SYNTAX Unsigned32 (0..1000)
            MAX-ACCESS read-only
            STATUS current
            DESCRIPTION
                "Bus voltage  of the Rectifier Cabinet. 
                Its value range: 0 to 100, 
                unit: V, 
                and the value is accurate to one decimal space (.1).  
                If the value is 2147483647(0x7FFFFFFF), it indicates that the value is invalid."
            ::= { hwRectifierCabinetInfoEntry 4 }

        hwRectifierCabinetCabinetModel OBJECT-TYPE
            SYNTAX OCTET STRING
            MAX-ACCESS read-only
            STATUS current
            DESCRIPTION
                "The cabinet model of the Rectifier Cabinet."
            ::= { hwRectifierCabinetInfoEntry 5 }

        hwAcCabinet OBJECT IDENTIFIER ::= { hwSiteMonitorMIBObjects 38 }

        hwAcCabinetInfoTable OBJECT-TYPE
            SYNTAX SEQUENCE OF HwAcCabinetInfoEntry
            MAX-ACCESS not-accessible
             STATUS current
             DESCRIPTION
                "/"
            ::= { hwAcCabinet 1 }

        hwAcCabinetInfoEntry OBJECT-TYPE
                        SYNTAX HwAcCabinetInfoEntry
            MAX-ACCESS not-accessible
             STATUS current
             DESCRIPTION
                "/"
            INDEX { hwAcCabinetIndex }
            ::= { hwAcCabinetInfoTable 1 }

        HwAcCabinetInfoEntry            ::= SEQUENCE {
                hwAcCabinetIndex
                    Unsigned32,
                hwAcCabinetEquipId
                    Unsigned32,
                hwAcCabinetEquipName
                    OCTET STRING,
                hwACCabinetCabinetModel
                    OCTET STRING,
                hwACCabinetIndoorTemperature
                    Integer32,
                hwACCabinetCommunicationAddress
                    Unsigned32
            }

        hwAcCabinetIndex OBJECT-TYPE
            SYNTAX Unsigned32
            MAX-ACCESS read-only
            STATUS current
            DESCRIPTION
                "The Ac Cabinet Index."
            ::= { hwAcCabinetInfoEntry 1 }

        hwAcCabinetEquipId OBJECT-TYPE
            SYNTAX Unsigned32
            MAX-ACCESS read-only
            STATUS current
            DESCRIPTION
                "The Ac Cabinet equip ID no."
            ::= { hwAcCabinetInfoEntry 2 }

        hwAcCabinetEquipName OBJECT-TYPE
            SYNTAX OCTET STRING (SIZE (0..63))
            MAX-ACCESS read-only
            STATUS current
            DESCRIPTION
                "The Ac Cabinet equip name."
            ::= { hwAcCabinetInfoEntry 3 }

        hwACCabinetCabinetModel OBJECT-TYPE
            SYNTAX OCTET STRING
            MAX-ACCESS read-only
            STATUS current
            DESCRIPTION
                "System type name of the AC Cabinet."
            ::= { hwAcCabinetInfoEntry 4 }

        hwACCabinetIndoorTemperature OBJECT-TYPE
            SYNTAX Integer32 ( -40..80)
            MAX-ACCESS read-only
            STATUS current
            DESCRIPTION
                "The temperatrue in the AC cabinet. It is a temperature collected in real time. 
                Value range: -40 to 80, 
                unit: centigrade (degC), 
                and the value is an integer .
                If the value is 2147483647(0x7FFFFFFF), it indicates that battery temperature sensor is not configured."
            ::= { hwAcCabinetInfoEntry 5 }

        hwACCabinetCommunicationAddress OBJECT-TYPE
            SYNTAX Unsigned32 (0..8)
            MAX-ACCESS read-only
            STATUS current
            DESCRIPTION
                "The communication address of the AC cabinet."
            ::= { hwAcCabinetInfoEntry 6 }

        hwController OBJECT IDENTIFIER ::= { hwSiteMonitorMIBObjects 39 }

        hwControllerInfoTable OBJECT-TYPE
            SYNTAX SEQUENCE OF HwControllerInfoEntry
            MAX-ACCESS not-accessible
             STATUS current
             DESCRIPTION
                "/"
            ::= { hwController 1 }

        hwControllerInfoEntry OBJECT-TYPE
                        SYNTAX HwControllerInfoEntry
            MAX-ACCESS not-accessible
             STATUS current
             DESCRIPTION
                "/"
            INDEX { hwControllerIndex }
            ::= { hwControllerInfoTable 1 }

        HwControllerInfoEntry            ::= SEQUENCE {
                hwControllerIndex
                    Unsigned32,
                hwControllerEquipId
                    Unsigned32,
                hwControllerEquipName
                    OCTET STRING,
                hwControllerFatherEquipname
                    OCTET STRING,
                hwControllerBuzzerEnable
                    INTEGER,
                hwControllerType
                    INTEGER
            }

        hwControllerIndex OBJECT-TYPE
            SYNTAX Unsigned32
            MAX-ACCESS read-only
            STATUS current
            DESCRIPTION
                "The Controller Index."
            ::= { hwControllerInfoEntry 1 }

        hwControllerEquipId OBJECT-TYPE
            SYNTAX Unsigned32
            MAX-ACCESS read-only
            STATUS current
            DESCRIPTION
                "The Controller equip ID no."
            ::= { hwControllerInfoEntry 2 }

        hwControllerEquipName OBJECT-TYPE
            SYNTAX OCTET STRING (SIZE (0..63))
            MAX-ACCESS read-only
            STATUS current
            DESCRIPTION
                "The Controller equip name."
            ::= { hwControllerInfoEntry 3 }

        hwControllerFatherEquipname OBJECT-TYPE
            SYNTAX OCTET STRING
            MAX-ACCESS read-only
            STATUS current
            DESCRIPTION
                "Name of the parent device of the Water Sensor"
            ::= { hwControllerInfoEntry 4 }

        hwControllerBuzzerEnable OBJECT-TYPE
            SYNTAX INTEGER
                {
                enable(1),
                disable(2),
                nullOper(255)
                }
            MAX-ACCESS read-write
            STATUS current
            DESCRIPTION
                "Buzzer enabling. It manually controls the enabling of the buzzer alarm. This node is of the enumeration type. 
                When the enumeration value is 1, it means to enable the buzzer;
                When the enumeration value is 2, it means to disable the buzzer. 
                When the enumeration value is 255, it means to nulloper the buzzer. 
                "
            ::= { hwControllerInfoEntry 5 }

        hwControllerType OBJECT-TYPE
            SYNTAX INTEGER
                {
                smu02b(1),
                smu02c(2),
                smu02s(3),
                smu02d(4),
                smu11b(5),
                wcu01(6),
                smu02c_x(7),
                scc800_s(8),
                e_iot(9),
                smu06t2(10),
                smu02x_e(11),
                smu02c1(12),
                isitepower_m(13),
                smu11c(14),
                dps(15),
                smu11d(16),
                acb_iot(17),
                ibreaker(18),
                smu02c2(19),
                unknown(255)
                }
            MAX-ACCESS read-only
            STATUS current
            DESCRIPTION
                "Controller type.Value range: SMU02B is 0, SMU02C is 1, SMU02S is 2, SMU02D is 3, SMU11B is 4, WCU01 is 5, SMU02C_X is 6, SCC800_S is 7, E_IOT is 8, SMU06T2 is 9, SMU02X_E is 10, SMU02C1 is 11, ISITEPOWER_M is 12, SMU11C is 14, ACB_IOT is 19, IBREAKER is 20, SMU02C2 is 21."
            ::= { hwControllerInfoEntry 6 }

        hwDeviceUim OBJECT IDENTIFIER ::= { hwSiteMonitorMIBObjects 40 }

        hwDeviceUimInfoTable OBJECT-TYPE
            SYNTAX SEQUENCE OF HwDeviceUimInfoEntry
            MAX-ACCESS not-accessible
             STATUS current
             DESCRIPTION
                "/"
            ::= { hwDeviceUim 1 }

        hwDeviceUimInfoEntry OBJECT-TYPE
                        SYNTAX HwDeviceUimInfoEntry
            MAX-ACCESS not-accessible
             STATUS current
             DESCRIPTION
                "/"
            INDEX { hwDeviceUimIndex }
            ::= { hwDeviceUimInfoTable 1 }

        HwDeviceUimInfoEntry            ::= SEQUENCE {
                hwDeviceUimIndex
                    Unsigned32,
                hwDeviceUimEquipId
                    Unsigned32,
                hwDeviceUimEquipName
                    OCTET STRING,
                hwDeviceUimFatherEquipname
                    OCTET STRING
            }

        hwDeviceUimIndex OBJECT-TYPE
            SYNTAX Unsigned32
            MAX-ACCESS read-only
            STATUS current
            DESCRIPTION
                "Table index of the UIM."
            ::= { hwDeviceUimInfoEntry 1 }

        hwDeviceUimEquipId OBJECT-TYPE
            SYNTAX Unsigned32
            MAX-ACCESS read-only
            STATUS current
            DESCRIPTION
                "Device ID of the UIM."
            ::= { hwDeviceUimInfoEntry 2 }

        hwDeviceUimEquipName OBJECT-TYPE
            SYNTAX OCTET STRING (SIZE (0..63))
            MAX-ACCESS read-only
            STATUS current
            DESCRIPTION
                "Device name of the UIM."
            ::= { hwDeviceUimInfoEntry 3 }

        hwDeviceUimFatherEquipname OBJECT-TYPE
            SYNTAX OCTET STRING
            MAX-ACCESS read-only
            STATUS current
            DESCRIPTION
                "Name of the parent device of the UIM."
            ::= { hwDeviceUimInfoEntry 4 }

        hwLocalDCPower OBJECT IDENTIFIER ::= { hwSiteMonitorMIBObjects 41 }

        hwLocalDCPowerInfoTable OBJECT-TYPE
            SYNTAX SEQUENCE OF HwLocalDCPowerInfoEntry
            MAX-ACCESS not-accessible
             STATUS current
             DESCRIPTION
                "/"
            ::= { hwLocalDCPower 1 }

        hwLocalDCPowerInfoEntry OBJECT-TYPE
                        SYNTAX HwLocalDCPowerInfoEntry
            MAX-ACCESS not-accessible
             STATUS current
             DESCRIPTION
                "/"
            INDEX { hwLocalDCPowerIndex }
            ::= { hwLocalDCPowerInfoTable 1 }

        HwLocalDCPowerInfoEntry            ::= SEQUENCE {
                hwLocalDCPowerIndex
                    Unsigned32,
                hwLocalDCPowerEquipId
                    Unsigned32,
                hwLocalDCPowerEquipName
                    OCTET STRING
            }

        hwLocalDCPowerIndex OBJECT-TYPE
            SYNTAX Unsigned32
            MAX-ACCESS read-only
            STATUS current
            DESCRIPTION
                "Table index of the Local DC Power."
            ::= { hwLocalDCPowerInfoEntry 1 }

        hwLocalDCPowerEquipId OBJECT-TYPE
            SYNTAX Unsigned32
            MAX-ACCESS read-only
            STATUS current
            DESCRIPTION
                "Device ID of the Local DC Power."
            ::= { hwLocalDCPowerInfoEntry 2 }

        hwLocalDCPowerEquipName OBJECT-TYPE
            SYNTAX OCTET STRING (SIZE (0..63))
            MAX-ACCESS read-only
            STATUS current
            DESCRIPTION
                "Device name of the Local DC Power."
            ::= { hwLocalDCPowerInfoEntry 3 }

        hwACSamplingUnit OBJECT IDENTIFIER ::= { hwSiteMonitorMIBObjects 42 }

        hwACSamplingUnitInfoTable OBJECT-TYPE
            SYNTAX SEQUENCE OF HwACSamplingUnitInfoEntry
            MAX-ACCESS not-accessible
             STATUS current
             DESCRIPTION
                "/"
            ::= { hwACSamplingUnit 1 }

        hwACSamplingUnitInfoEntry OBJECT-TYPE
                        SYNTAX HwACSamplingUnitInfoEntry
            MAX-ACCESS not-accessible
             STATUS current
             DESCRIPTION
                "/"
            INDEX { hwACSamplingUnitIndex }
            ::= { hwACSamplingUnitInfoTable 1 }

        HwACSamplingUnitInfoEntry            ::= SEQUENCE {
                hwACSamplingUnitIndex
                    Unsigned32,
                hwACSamplingUnitEquipId
                    Unsigned32,
                hwACSamplingUnitEquipName
                    OCTET STRING
            }

        hwACSamplingUnitIndex OBJECT-TYPE
            SYNTAX Unsigned32
            MAX-ACCESS read-only
            STATUS current
            DESCRIPTION
                "Table index of the AC Sampling Unit."
            ::= { hwACSamplingUnitInfoEntry 1 }

        hwACSamplingUnitEquipId OBJECT-TYPE
            SYNTAX Unsigned32
            MAX-ACCESS read-only
            STATUS current
            DESCRIPTION
                "Device ID of the AC Sampling Unit."
            ::= { hwACSamplingUnitInfoEntry 2 }

        hwACSamplingUnitEquipName OBJECT-TYPE
            SYNTAX OCTET STRING (SIZE (0..63))
            MAX-ACCESS read-only
            STATUS current
            DESCRIPTION
                "Device name of the AC Sampling Unit."
            ::= { hwACSamplingUnitInfoEntry 3 }

        hwDCSamplingUnit OBJECT IDENTIFIER ::= { hwSiteMonitorMIBObjects 43 }

        hwDCSamplingUnitInfoTable OBJECT-TYPE
            SYNTAX SEQUENCE OF HwDCSamplingUnitInfoEntry
            MAX-ACCESS not-accessible
             STATUS current
             DESCRIPTION
                "/"
            ::= { hwDCSamplingUnit 1 }

        hwDCSamplingUnitInfoEntry OBJECT-TYPE
                        SYNTAX HwDCSamplingUnitInfoEntry
            MAX-ACCESS not-accessible
             STATUS current
             DESCRIPTION
                "/"
            INDEX { hwDCSamplingUnitIndex }
            ::= { hwDCSamplingUnitInfoTable 1 }

        HwDCSamplingUnitInfoEntry            ::= SEQUENCE {
                hwDCSamplingUnitIndex
                    Unsigned32,
                hwDCSamplingUnitEquipId
                    Unsigned32,
                hwDCSamplingUnitEquipName
                    OCTET STRING
            }

        hwDCSamplingUnitIndex OBJECT-TYPE
            SYNTAX Unsigned32
            MAX-ACCESS read-only
            STATUS current
            DESCRIPTION
                "Table index of the DC Sampling Unit."
            ::= { hwDCSamplingUnitInfoEntry 1 }

        hwDCSamplingUnitEquipId OBJECT-TYPE
            SYNTAX Unsigned32
            MAX-ACCESS read-only
            STATUS current
            DESCRIPTION
                "Device ID of the DC Sampling Unit."
            ::= { hwDCSamplingUnitInfoEntry 2 }

        hwDCSamplingUnitEquipName OBJECT-TYPE
            SYNTAX OCTET STRING (SIZE (0..63))
            MAX-ACCESS read-only
            STATUS current
            DESCRIPTION
                "Device name of the DC Sampling Unit."
            ::= { hwDCSamplingUnitInfoEntry 3 }

        hwSiteHWInverter OBJECT IDENTIFIER ::= { hwSiteMonitorMIBObjects 44 }

        hwHWInverterUnit OBJECT IDENTIFIER ::= { hwSiteHWInverter 1 }

        hwHWInverterUnitSampTable OBJECT-TYPE
            SYNTAX SEQUENCE OF HwHWInverterUnitSampEntry
            MAX-ACCESS not-accessible
             STATUS current
             DESCRIPTION
                "/"
            ::= { hwHWInverterUnit 1 }

        hwHWInverterUnitSampEntry OBJECT-TYPE
                        SYNTAX HwHWInverterUnitSampEntry
            MAX-ACCESS not-accessible
             STATUS current
             DESCRIPTION
                "/"
            INDEX { hwHWInverterUnitId }
            ::= { hwHWInverterUnitSampTable 1 }

        HwHWInverterUnitSampEntry            ::= SEQUENCE {
                hwHWInverterUnitId
                    Unsigned32,
                hwHWInverterUnitName
                    OCTET STRING,
                hwHWInverterUnitModel
                    OCTET STRING,
                hwHWInverterUnitQuantityOfInverter
                    Unsigned32,
                hwHWInverterUnitBarcode
                    OCTET STRING,
                hwHWInverterUnitInputVoltage
                    Unsigned32,
                hwHWInverterUnitInputPower
                    Unsigned32,
                hwHWInverterUnitInputCurrent
                    Unsigned32,
                hwHWInverterUnitOutputVoltage
                    Unsigned32,
                hwHWInverterUnitOutputCurrent
                    Unsigned32,
                hwHWInverterUnitOutputACFrequency
                    Unsigned32,
                hwHWInverterUnitOutputPowerFactor
                    Integer32,
                hwHWInverterUnitOutputL1PhaseVoltage
                    Unsigned32,
                hwHWInverterUnitOutputL2PhaseVoltage
                    Unsigned32,
                hwHWInverterUnitOutputL3PhaseVoltage
                    Unsigned32,
                hwHWInverterUnitOutputL1PhaseCurrent
                    Unsigned32,
                hwHWInverterUnitOutputL2PhaseCurrent
                    Unsigned32,
                hwHWInverterUnitOutputL3PhaseCurrent
                    Unsigned32,
                hwHWInverterUnitOutputL1PhasePowerFactor
                    Integer32,
                hwHWInverterUnitOutputL2PhasePowerFactor
                    Integer32,
                hwHWInverterUnitOutputL3PhasePowerFactor
                    Integer32,
                hwHWInverterUnitActivePower
                    Unsigned32,
                hwHWInverterUnitApparentPower
                    Unsigned32,
                hwHWinverterUnitFatherEquipName
                    OCTET STRING,
                hwHWInverterUnitLoadRate
                    Unsigned32
            }

        hwHWInverterUnitId OBJECT-TYPE
            SYNTAX Unsigned32
            MAX-ACCESS read-only
            STATUS current
            DESCRIPTION
                "Device ID of the inverter unit module. "
            ::= { hwHWInverterUnitSampEntry 1 }

        hwHWInverterUnitName OBJECT-TYPE
            SYNTAX OCTET STRING (SIZE (0..63))
            MAX-ACCESS read-only
            STATUS current
            DESCRIPTION
                "Name of the inverter unit module group, character string type, is used to specify the rectifier module group."
            ::= { hwHWInverterUnitSampEntry 2 }

        hwHWInverterUnitModel OBJECT-TYPE
            SYNTAX OCTET STRING (SIZE (0..63))
            MAX-ACCESS read-only
            STATUS current
            DESCRIPTION
                "Model of the inverter unit. "
            ::= { hwHWInverterUnitSampEntry 3 }

        hwHWInverterUnitQuantityOfInverter OBJECT-TYPE
            SYNTAX Unsigned32 (0..60)
            MAX-ACCESS read-only
            STATUS current
            DESCRIPTION
                "Total quantity of the Inverter modules. Value range: 0 to 60. unit:pcs."
            ::= { hwHWInverterUnitSampEntry 4 }

        hwHWInverterUnitBarcode OBJECT-TYPE
            SYNTAX OCTET STRING (SIZE (0..63))
            MAX-ACCESS read-only
            STATUS current
            DESCRIPTION
                "Barcode of the inverter unit. "
            ::= { hwHWInverterUnitSampEntry 5 }

        hwHWInverterUnitInputVoltage OBJECT-TYPE
            SYNTAX Unsigned32 (0..4000)
            MAX-ACCESS read-only
            STATUS current
            DESCRIPTION
                "Input voltage of the inverter unit. It is a real-time analog parameter. Value range: 0 to 400, unit: V, the value is accurate to one decimal place (.1). If the value is 2147483647(0x7FFFFFFF), it indicates that the value is invalid."
            ::= { hwHWInverterUnitSampEntry 6 }

        hwHWInverterUnitInputPower OBJECT-TYPE
            SYNTAX Unsigned32 (0..240000)
            MAX-ACCESS read-only
            STATUS current
            DESCRIPTION
                "Input power of the inverter unit. It is a real-time analog parameter. Value range: 0 to 2400, unit: kW, the value is accurate to two decimal place (.01). If the value is 2147483647(0x7FFFFFFF), it indicates that the value is invalid."
            ::= { hwHWInverterUnitSampEntry 7 }

        hwHWInverterUnitInputCurrent OBJECT-TYPE
            SYNTAX Unsigned32 (0..60000)
            MAX-ACCESS read-only
            STATUS current
            DESCRIPTION
                "Input current of the inverter unit. It is a real-time analog parameter. Value range: 0 to 6000, unit: A, the value is accurate to one decimal place (.1). If the value is 2147483647(0x7FFFFFFF), it indicates that the value is invalid."
            ::= { hwHWInverterUnitSampEntry 8 }

        hwHWInverterUnitOutputVoltage OBJECT-TYPE
            SYNTAX Unsigned32 (0..3000)
            MAX-ACCESS read-only
            STATUS current
            DESCRIPTION
                "Output voltage of the inverter unit. It is a real-time analog parameter. Value range: 0 to 300, unit: V, the value is accurate to one decimal place (.1). If the value is 2147483647(0x7FFFFFFF), it indicates that the value is invalid."
            ::= { hwHWInverterUnitSampEntry 9 }

        hwHWInverterUnitOutputCurrent OBJECT-TYPE
            SYNTAX Unsigned32 (0..10000)
            MAX-ACCESS read-only
            STATUS current
            DESCRIPTION
                "Output current of the inverter unit. It is a real-time analog parameter. Value range: 0 to 1000, unit: A, the value is accurate to one decimal place (.1). If the value is 2147483647(0x7FFFFFFF), it indicates that the value is invalid."
            ::= { hwHWInverterUnitSampEntry 10 }

        hwHWInverterUnitOutputACFrequency OBJECT-TYPE
            SYNTAX Unsigned32 (0..1000)
            MAX-ACCESS read-only
            STATUS current
            DESCRIPTION
                "AC frequency of the inverter unit. It is a real-time analog parameter. Value range: 0 to 100, unit: Hz, the value is accurate to one decimal place (.1). If the value is 2147483647(0x7FFFFFFF), it indicates that the value is invalid."
            ::= { hwHWInverterUnitSampEntry 11 }

        hwHWInverterUnitOutputPowerFactor OBJECT-TYPE
            SYNTAX Integer32 (-1000..1000)
            MAX-ACCESS read-only
            STATUS current
            DESCRIPTION
                "Power factor of the inverter unit. It is a real-time analog parameter. Value range: -1 to 1, unit: NA, the value is accurate to three decimal place (.001). If the value is 2147483647(0x7FFFFFFF), it indicates that the value is invalid."
            ::= { hwHWInverterUnitSampEntry 12 }

        hwHWInverterUnitOutputL1PhaseVoltage OBJECT-TYPE
            SYNTAX Unsigned32 (0..8000)
            MAX-ACCESS read-only
            STATUS current
            DESCRIPTION
                "Output L1 Phase voltage of the inverter unit. It is a real-time analog parameter. Value range: 0 to 800, unit: V, the value is accurate to one decimal place (.1). If the value is 2147483647(0x7FFFFFFF), it indicates that the value is invalid."
            ::= { hwHWInverterUnitSampEntry 13 }

        hwHWInverterUnitOutputL2PhaseVoltage OBJECT-TYPE
            SYNTAX Unsigned32 (0..8000)
            MAX-ACCESS read-only
            STATUS current
            DESCRIPTION
                "Output L2 Phase voltage of the inverter unit. It is a real-time analog parameter. Value range: 0 to 800, unit: V, the value is accurate to one decimal place (.1). If the value is 2147483647(0x7FFFFFFF), it indicates that the value is invalid."
            ::= { hwHWInverterUnitSampEntry 14 }

        hwHWInverterUnitOutputL3PhaseVoltage OBJECT-TYPE
            SYNTAX Unsigned32 (0..8000)
            MAX-ACCESS read-only
            STATUS current
            DESCRIPTION
                "Output L3 Phase voltage of the inverter unit. It is a real-time analog parameter. Value range: 0 to 800, unit: V, the value is accurate to one decimal place (.1). If the value is 2147483647(0x7FFFFFFF), it indicates that the value is invalid."
            ::= { hwHWInverterUnitSampEntry 15 }

        hwHWInverterUnitOutputL1PhaseCurrent OBJECT-TYPE
            SYNTAX Unsigned32 (0..10000)
            MAX-ACCESS read-only
            STATUS current
            DESCRIPTION
                "Output L1 Phase current of the inverter unit. It is a real-time analog parameter. Value range: 0 to 1000, unit: A, the value is accurate to one decimal place (.1). If the value is 2147483647(0x7FFFFFFF), it indicates that the value is invalid."
            ::= { hwHWInverterUnitSampEntry 16 }

        hwHWInverterUnitOutputL2PhaseCurrent OBJECT-TYPE
            SYNTAX Unsigned32 (0..10000)
            MAX-ACCESS read-only
            STATUS current
            DESCRIPTION
                "Output L2 Phase current of the inverter unit. It is a real-time analog parameter. Value range: 0 to 1000, unit: A, the value is accurate to one decimal place (.1). If the value is 2147483647(0x7FFFFFFF), it indicates that the value is invalid."
            ::= { hwHWInverterUnitSampEntry 17 }

        hwHWInverterUnitOutputL3PhaseCurrent OBJECT-TYPE
            SYNTAX Unsigned32 (0..10000)
            MAX-ACCESS read-only
            STATUS current
            DESCRIPTION
                "Output L3 Phase current of the inverter unit. It is a real-time analog parameter. Value range: 0 to 1000, unit: A, the value is accurate to one decimal place (.1). If the value is 2147483647(0x7FFFFFFF), it indicates that the value is invalid."
            ::= { hwHWInverterUnitSampEntry 18 }

        hwHWInverterUnitOutputL1PhasePowerFactor OBJECT-TYPE
            SYNTAX Integer32 (-100..100)
            MAX-ACCESS read-only
            STATUS current
            DESCRIPTION
                "L1 Phase power factor of the inverter unit. It is a real-time analog parameter. Value range: -1 to 1, unit: NA, the value is accurate to two decimal place (.01). If the value is 2147483647(0x7FFFFFFF), it indicates that the value is invalid."
            ::= { hwHWInverterUnitSampEntry 19 }

        hwHWInverterUnitOutputL2PhasePowerFactor OBJECT-TYPE
            SYNTAX Integer32 (-100..100)
            MAX-ACCESS read-only
            STATUS current
            DESCRIPTION
                "L2 Phase power factor of the inverter unit. It is a real-time analog parameter. Value range: -1 to 1, unit: NA, the value is accurate to two decimal place (.01). If the value is 2147483647(0x7FFFFFFF), it indicates that the value is invalid."
            ::= { hwHWInverterUnitSampEntry 20 }

        hwHWInverterUnitOutputL3PhasePowerFactor OBJECT-TYPE
            SYNTAX Integer32 (-100..100)
            MAX-ACCESS read-only
            STATUS current
            DESCRIPTION
                "L3 Phase power factor of the inverter unit. It is a real-time analog parameter. Value range: -1 to 1, unit: NA, the value is accurate to two decimal place (.01). If the value is 2147483647(0x7FFFFFFF), it indicates that the value is invalid."
            ::= { hwHWInverterUnitSampEntry 21 }

        hwHWInverterUnitActivePower OBJECT-TYPE
            SYNTAX Unsigned32 (0..240000)
            MAX-ACCESS read-only
            STATUS current
            DESCRIPTION
                "Active power of the inverter unit. It is a real-time analog parameter. Value range: 0 to 2400, unit: kW, the value is accurate to two decimal place (.01). If the value is 2147483647(0x7FFFFFFF), it indicates that the value is invalid."
            ::= { hwHWInverterUnitSampEntry 22 }

        hwHWInverterUnitApparentPower OBJECT-TYPE
            SYNTAX Unsigned32 (0..240000)
            MAX-ACCESS read-only
            STATUS current
            DESCRIPTION
                "Apparent power of the inverter unit. It is a real-time analog parameter. Value range: 0 to 2400, unit: kVA, the value is accurate to two decimal place (.01). If the value is 2147483647(0x7FFFFFFF), it indicates that the value is invalid."
            ::= { hwHWInverterUnitSampEntry 23 }

        hwHWinverterUnitFatherEquipName OBJECT-TYPE
            SYNTAX OCTET STRING (SIZE (0..63))
            MAX-ACCESS read-only
            STATUS current
            DESCRIPTION
                "Name of the parent device of the inverter unit."
            ::= { hwHWInverterUnitSampEntry 24 }

        hwHWInverterUnitLoadRate OBJECT-TYPE
            SYNTAX Unsigned32 (0..150)
            MAX-ACCESS read-only
            STATUS current
            DESCRIPTION
                "Load rate of the inverter unit. It is a real-time analog parameter. Value range: 0 to 150, unit: %, and its value is an integer (1).  
                If the value is 2147483647(0x7FFFFFFF), it indicates that the value is invalid."
            ::= { hwHWInverterUnitSampEntry 25 }

        hwHWInverterUnitSetTable OBJECT-TYPE
            SYNTAX SEQUENCE OF HwHWInverterUnitSetEntry
            MAX-ACCESS not-accessible
             STATUS current
             DESCRIPTION
                "/"
            ::= { hwHWInverterUnit 2 }

        hwHWInverterUnitSetEntry OBJECT-TYPE
                        SYNTAX HwHWInverterUnitSetEntry
            MAX-ACCESS not-accessible
             STATUS current
             DESCRIPTION
                "/"
            INDEX { hwHWInverterUnitOutputVoltageType }
            ::= { hwHWInverterUnitSetTable 1 }

        HwHWInverterUnitSetEntry            ::= SEQUENCE {
                hwHWInverterUnitOutputVoltageType
                    INTEGER,
                hwHWInverterUnitOutputFrequency
                    INTEGER,
                hwHWInverterUnitOutputMode
                    INTEGER,
                hwHWInverterUnitFanControlMode
                    INTEGER,
                hwHWInverterUnitUpperInputProtectionVoltage 
                    Integer32,
                hwHWInverterUnitLowerInputProtectionVoltage 
                    Integer32,
                hwHWInverterUnitUpperOutputProtectionVoltage 
                    Integer32,
                hwHWInverterUnitLowerOutputProtectionVoltage 
                    Integer32,
                hwHWInverterUnitFanSpeedControl
                    Integer32,
                hwHWInverterUnitDeleteCommunicationFailureEquip
                    INTEGER,
                hwHWInverterUnitLowerInputHysteresisVolt
                    Unsigned32,
                hwHWInverterUnitCabinetNum
                    OCTET STRING,
                hwHWInverterUnitOnOffControl
                    INTEGER
            }

        hwHWInverterUnitOutputVoltageType OBJECT-TYPE
            SYNTAX INTEGER
                {
                voltage200(1),
                voltage208(2),
                voltage220(3),
                voltage230(4),
                voltage240(5),
                unknown(255)
                }
            MAX-ACCESS read-write
            STATUS current
            DESCRIPTION
                "Output voltage type of the inverter unit module. It is an enumeration type:
                If the enumeration value is 1, it indicates 200V; 
                If the enumeration value is 2, it indicates 208V;
                If the enumeration value is 3, it indicates 220V; 
                If the enumeration value is 4, it indicates 230V;
                If the enumeration value is 5, it indicates 240V;
                If the enumeration value is 255, it indicates unkown type."
            ::= { hwHWInverterUnitSetEntry 1 }

        hwHWInverterUnitOutputFrequency OBJECT-TYPE
            SYNTAX INTEGER
                {
                frequency50(1),
                frequency60(2),
                unknown(255)
                }
            MAX-ACCESS read-write
            STATUS current
            DESCRIPTION
                "Output frequency of the inverter unit module. It is an enumeration type:
                If the enumeration value is 1, it indicates 50 Hz; 
                If the enumeration value is 2, it indicates 60 Hz;
                If the enumeration value is 255, it indicates unkown type."
            ::= { hwHWInverterUnitSetEntry 2 }

        hwHWInverterUnitOutputMode OBJECT-TYPE
            SYNTAX INTEGER
                {
                bypassFirst(1),
                invertFirst(2),
                unknown(255)
                }
            MAX-ACCESS read-write
            STATUS current
            DESCRIPTION
                "Output mode of the inverter unit module. It is an enumeration type:
                If the enumeration value is 1, it indicates BypassFirst; 
                If the enumeration value is 2, it indicates InvertFirst."
            ::= { hwHWInverterUnitSetEntry 4 }

        hwHWInverterUnitFanControlMode OBJECT-TYPE
            SYNTAX INTEGER
                {
                auto(1),
                fullSpeed(2),
                unknown(255)
                }
            MAX-ACCESS read-write
            STATUS current
            DESCRIPTION
                "Fan control mode of the inverter unit module. It is an enumeration type:
                If the enumeration value is 1, it indicates Auto; 
                If the enumeration value is 2, it indicates Full Speed."
            ::= { hwHWInverterUnitSetEntry 6 }

        hwHWInverterUnitUpperInputProtectionVoltage  OBJECT-TYPE
            SYNTAX Integer32 (560..600)
            MAX-ACCESS read-write
            STATUS current
            DESCRIPTION
                "Upper input protection voltage, It can be configured by users. 
                Its value range: 56 to 60, 
                unit: V, 
                and the value is accurate to one decimal space (.1).  
                If the value is 2147483647(0x7FFFFFFF), it indicates that the value is invalid."
            ::= { hwHWInverterUnitSetEntry 7 }

        hwHWInverterUnitLowerInputProtectionVoltage  OBJECT-TYPE
            SYNTAX Integer32 (410..480)
            MAX-ACCESS read-write
            STATUS current
            DESCRIPTION
                "Lower input protection voltage, It can be configured by users. 
                Its value range: 41 to 48, 
                unit: V, 
                and the value is accurate to one decimal space (.1).  
                If the value is 2147483647(0x7FFFFFFF), it indicates that the value is invalid."
            ::= { hwHWInverterUnitSetEntry 8 }

        hwHWInverterUnitUpperOutputProtectionVoltage  OBJECT-TYPE
            SYNTAX Integer32 (110..135)
            MAX-ACCESS read-write
            STATUS current
            DESCRIPTION
                "Upper output protection voltage, It can be configured by users. 
                Its value range: 110 to 135, 
                unit: %, 
                and its value is an integer (1).  
                If the value is 2147483647(0x7FFFFFFF), it indicates that the value is invalid."
            ::= { hwHWInverterUnitSetEntry 9 }

        hwHWInverterUnitLowerOutputProtectionVoltage  OBJECT-TYPE
            SYNTAX Integer32 (65..90)
            MAX-ACCESS read-write
            STATUS current
            DESCRIPTION
                "Lower output protection voltage, It can be configured by users. 
                Its value range: 65 to 90, 
                unit: %, 
                and its value is an integer (1).  
                If the value is 2147483647(0x7FFFFFFF), it indicates that the value is invalid."
            ::= { hwHWInverterUnitSetEntry 10 }

        hwHWInverterUnitFanSpeedControl OBJECT-TYPE
            SYNTAX Integer32 (1..100)
            MAX-ACCESS read-write
            STATUS current
            DESCRIPTION
                "Fan speed control, It can be configured by users. 
                Its value range: 1 to 100, 
                unit: %, 
                and its value is an integer (1).  
                If the value is 2147483647(0x7FFFFFFF), it indicates that the value is invalid."
            ::= { hwHWInverterUnitSetEntry 11 }

        hwHWInverterUnitDeleteCommunicationFailureEquip OBJECT-TYPE
            SYNTAX INTEGER
                {
                yes(2)
                }
            MAX-ACCESS read-write
            STATUS current
            DESCRIPTION
                "Delete communication failure equipments of the inverter unit module. It is an enumeration type:
                If the enumeration value is 2, it indicates that deletes communication failure equipments; "
            ::= { hwHWInverterUnitSetEntry 12 }

        hwHWInverterUnitLowerInputHysteresisVolt OBJECT-TYPE
            SYNTAX Unsigned32 (3..5)
            MAX-ACCESS read-write
            STATUS current
            DESCRIPTION
                "Hysteresis point of the lower input voltage. 
                Its value range: 3 to 5, 
                unit: V, 
                and its value is an integer (1).  
                If the value is 2147483647(0x7FFFFFFF), it indicates that the value is invalid."
            ::= { hwHWInverterUnitSetEntry 14 }

        hwHWInverterUnitCabinetNum OBJECT-TYPE
            SYNTAX OCTET STRING (SIZE (0..30))
            MAX-ACCESS read-write
            STATUS current
            DESCRIPTION
                "Cabinet number of the inverter unit. It is a real-time analog parameter. Value range: 0 to 30, and its value is an integer (1).
                If the value is 2147483647(0x7FFFFFFF), it indicates that the value is invalid."
            ::= { hwHWInverterUnitSetEntry 15 }

        hwHWInverterUnitOnOffControl OBJECT-TYPE
            SYNTAX INTEGER
                {
                on(1),
                off(2),
                nulloper(255)
                }
            MAX-ACCESS read-write
            STATUS current
            DESCRIPTION
                "Power-on or power-off of the inverter unit. It is an enumeration value:
                If the NMS notifies the SNMP agent that this node is set to 1, it indicates power-on of the inverter unit;
                If the NMS notifies the SNMP agent that this node is set to 2, it indicates power-off of the inverter unit.
                If the NMS notifies the SNMP agent that this node is set to 255, it indicates nullOper of the inverter unit."
            ::= { hwHWInverterUnitSetEntry 13 }

        hwECM OBJECT IDENTIFIER ::= { hwSiteHWInverter 2 }

        hwECMSampTable OBJECT-TYPE
            SYNTAX SEQUENCE OF HwECMSampEntry
            MAX-ACCESS not-accessible
             STATUS current
             DESCRIPTION
                "/"
            ::= { hwECM 1 }

        hwECMSampEntry OBJECT-TYPE
                        SYNTAX HwECMSampEntry
            MAX-ACCESS not-accessible
             STATUS current
             DESCRIPTION
                "/"
            INDEX { hwECMSampIndex }
            ::= { hwECMSampTable 1 }

        HwECMSampEntry            ::= SEQUENCE {
                hwECMSampIndex
                    Integer32,
                hwECMEquipId
                    Unsigned32,
                hwECMEquipName
                    OCTET STRING,
                hwECMBarcode
                    OCTET STRING,
                hwECMSoftwareVersion
                    OCTET STRING,
                hwECMHardwareVersion
                    OCTET STRING,
                hwECMDeviceAddress
                    Unsigned32,
                hwECMInputDCVoltage
                    Unsigned32,
                hwECMInputDCCurrent
                    Unsigned32,
                hwECMInputDCPower
                    Unsigned32,
                hwECMOutputVoltage
                    Unsigned32,
                hwECMOutputCurrent
                    Unsigned32,
                hwECMOutputFrequency
                    Unsigned32,
                hwECMOutputActivePower
                    Unsigned32,
                hwECMOutputApparentPower
                    Unsigned32,
                hwECMOutputPowerFactor
                    Integer32,
                hwECMWorkState
                    INTEGER,
                hwECMFatherEquipName
                    OCTET STRING
            }

        hwECMSampIndex OBJECT-TYPE
            SYNTAX Integer32
            MAX-ACCESS read-only
            STATUS current
            DESCRIPTION
                "Table index of the running ECM modules."
            ::= { hwECMSampEntry 1 }

        hwECMEquipId OBJECT-TYPE
            SYNTAX Unsigned32
            MAX-ACCESS read-only
            STATUS current
            DESCRIPTION
                "ECM module ID."
            ::= { hwECMSampEntry 2 }

        hwECMEquipName OBJECT-TYPE
            SYNTAX OCTET STRING (SIZE (0..63))
            MAX-ACCESS read-only
            STATUS current
            DESCRIPTION
                "Device name of the ECM module, character string type, is used to specify the ECM module. "
            ::= { hwECMSampEntry 3 }

        hwECMBarcode OBJECT-TYPE
            SYNTAX OCTET STRING (SIZE (0..63))
            MAX-ACCESS read-only
            STATUS current
            DESCRIPTION
                "Barcode of the ECM module. "
            ::= { hwECMSampEntry 4 }

        hwECMSoftwareVersion OBJECT-TYPE
            SYNTAX OCTET STRING (SIZE (0..63))
            MAX-ACCESS read-only
            STATUS current
            DESCRIPTION
                "Software version of the ECM module. "
            ::= { hwECMSampEntry 5 }

        hwECMHardwareVersion OBJECT-TYPE
            SYNTAX OCTET STRING (SIZE (0..63))
            MAX-ACCESS read-only
            STATUS current
            DESCRIPTION
                "Hardware version of the ECM module. "
            ::= { hwECMSampEntry 6 }

        hwECMDeviceAddress OBJECT-TYPE
            SYNTAX Unsigned32 (0..65535)
            MAX-ACCESS read-only
            STATUS current
            DESCRIPTION
                "Device address of the ECM module. Value range: 0 to 65535. unit:NA."
            ::= { hwECMSampEntry 7 }

        hwECMInputDCVoltage OBJECT-TYPE
            SYNTAX Unsigned32 (0..4000)
            MAX-ACCESS read-only
            STATUS current
            DESCRIPTION
                "Input voltage of the ECM module. It is a real-time analog parameter. Value range: 0 to 400, unit: V, the value is accurate to one decimal place (.1). If the value is 2147483647(0x7FFFFFFF), it indicates that the value is invalid."
            ::= { hwECMSampEntry 9 }

        hwECMInputDCCurrent OBJECT-TYPE
            SYNTAX Unsigned32 (0..100000)
            MAX-ACCESS read-only
            STATUS current
            DESCRIPTION
                "Input current of the ECM module. It is a real-time analog parameter. Value range: 0 to 10000, unit: A, the value is accurate to one decimal place (.1). If the value is 2147483647(0x7FFFFFFF), it indicates that the value is invalid."
            ::= { hwECMSampEntry 10 }

        hwECMInputDCPower OBJECT-TYPE
            SYNTAX Unsigned32 (0..240000)
            MAX-ACCESS read-only
            STATUS current
            DESCRIPTION
                "Input power of the ECM module. It is a real-time analog parameter. Value range: 0 to 2400, unit: kW, the value is accurate to two decimal place (.01). If the value is 2147483647(0x7FFFFFFF), it indicates that the value is invalid."
            ::= { hwECMSampEntry 11 }

        hwECMOutputVoltage OBJECT-TYPE
            SYNTAX Unsigned32 (0..3000)
            MAX-ACCESS read-only
            STATUS current
            DESCRIPTION
                "Output voltage of the ECM module. It is a real-time analog parameter. Value range: 0 to 300, unit: V, the value is accurate to one decimal place (.1). If the value is 2147483647(0x7FFFFFFF), it indicates that the value is invalid."
            ::= { hwECMSampEntry 12 }

        hwECMOutputCurrent OBJECT-TYPE
            SYNTAX Unsigned32 (0..10000)
            MAX-ACCESS read-only
            STATUS current
            DESCRIPTION
                "Output current of the ECM module. It is a real-time analog parameter. Value range: 0 to 1000, unit: A, the value is accurate to one decimal place (.1). If the value is 2147483647(0x7FFFFFFF), it indicates that the value is invalid."
            ::= { hwECMSampEntry 13 }

        hwECMOutputFrequency OBJECT-TYPE
            SYNTAX Unsigned32 (0..1000)
            MAX-ACCESS read-only
            STATUS current
            DESCRIPTION
                "AC frequency of the ECM. It is a real-time analog parameter. Value range: 0 to 100, unit: Hz, the value is accurate to one decimal place (.1). If the value is 2147483647(0x7FFFFFFF), it indicates that the value is invalid."
            ::= { hwECMSampEntry 14 }

        hwECMOutputActivePower OBJECT-TYPE
            SYNTAX Unsigned32 (0..40000)
            MAX-ACCESS read-only
            STATUS current
            DESCRIPTION
                "Active power of the ECM module. It is a real-time analog parameter. Value range: 0 to 400, unit: kW, the value is accurate to two decimal place (.01). If the value is 2147483647(0x7FFFFFFF), it indicates that the value is invalid."
            ::= { hwECMSampEntry 15 }

        hwECMOutputApparentPower OBJECT-TYPE
            SYNTAX Unsigned32 (0..40000)
            MAX-ACCESS read-only
            STATUS current
            DESCRIPTION
                "Apparent power of the ECM module. It is a real-time analog parameter. Value range: 0 to 400, unit: KVA, the value is accurate to two decimal place (.01). If the value is 2147483647(0x7FFFFFFF), it indicates that the value is invalid."
            ::= { hwECMSampEntry 16 }

        hwECMOutputPowerFactor OBJECT-TYPE
            SYNTAX Integer32 (-1000..1000)
            MAX-ACCESS read-only
            STATUS current
            DESCRIPTION
                "Power factor of the ECM module. It is a real-time analog parameter. Value range: -1 to 1, unit: NA, the value is accurate to three decimal place (.001). If the value is 2147483647(0x7FFFFFFF), it indicates that the value is invalid."
            ::= { hwECMSampEntry 17 }

        hwECMWorkState OBJECT-TYPE
            SYNTAX INTEGER
                {
                off(1),
                noOutput(2),
                bypass(3),
                inverting(4),
                unknown(255)
                }
            MAX-ACCESS read-only
            STATUS current
            DESCRIPTION
                "Work state of the ECM module. It is an enumeration type:
                If the enumeration value is 1, it indicates Off; 
                If the enumeration value is 2, it indicates No Output; 
                If the enumeration value is 3, it indicates Bypass; 
                If the enumeration value is 4, it indicates Inverting."
            ::= { hwECMSampEntry 18 }

        hwECMFatherEquipName OBJECT-TYPE
            SYNTAX OCTET STRING (SIZE (0..63))
            MAX-ACCESS read-only
            STATUS current
            DESCRIPTION
                "Name of the parent device of the ECM."
            ::= { hwECMSampEntry 19 }

        hwHWInverter OBJECT IDENTIFIER ::= { hwSiteHWInverter 3 }

        hwInverterModuleSampleTable OBJECT-TYPE
            SYNTAX SEQUENCE OF HwInverterModuleSampleEntry
            MAX-ACCESS not-accessible
             STATUS current
             DESCRIPTION
                "/"
            ::= { hwHWInverter 1 }

        hwInverterModuleSampleEntry OBJECT-TYPE
                        SYNTAX HwInverterModuleSampleEntry
            MAX-ACCESS not-accessible
             STATUS current
             DESCRIPTION
                "/"
            INDEX { hwInverterModuleSampIndex }
            ::= { hwInverterModuleSampleTable 1 }

        HwInverterModuleSampleEntry            ::= SEQUENCE {
                hwInverterModuleSampIndex
                    Integer32,
                hwInverterModuleEquipId
                    Unsigned32,
                hwInverterModuleEquipName
                    OCTET STRING,
                hwInverterModuleInputDCVoltage
                    Unsigned32,
                hwInverterModuleInputDCCurrent
                    Unsigned32,
                hwInverterModuleInputDCPower
                    Unsigned32,
                hwInverterModuleOutputVoltage
                    Unsigned32,
                hwInverterModuleOutputCurrent
                    Unsigned32,
                hwInverterModuleOutputFreqency
                    Unsigned32,
                hwInverterModuleOutputActivePower
                    Unsigned32,
                hwInverterModuleOutputApparentPower
                    Unsigned32,
                hwInverterModuleOutputPowerFactor
                    Integer32,
                hwInverterModuleTemperature
                    Integer32,
                hwInverterModuleWorkState
                    INTEGER,
                hwInverterModuleTotalRunTime
                    Unsigned32,
                hwInverterModuleRatedOutputPower
                    Unsigned32,
                hwInverterModuleRatedOutputVoltage
                    Unsigned32,
                hwInverterModuleRatedOutputFrequency
                    Unsigned32,
                hwInverterModuleRatedInputVoltage
                    Unsigned32,
                hwInverterModuleBarcode
                    OCTET STRING,
                hwInverterModuleSoftwareVersion
                    OCTET STRING,
                hwInverterModuleHardwareVersion
                    OCTET STRING,
                hwInverterModuleDeviceAddress
                    Unsigned32,
                hwInverterModuleFatherEquipName
                    OCTET STRING,
                hwHWInverterModulePhaseInfo
                    INTEGER
            }

        hwInverterModuleSampIndex OBJECT-TYPE
            SYNTAX Integer32
            MAX-ACCESS read-only
            STATUS current
            DESCRIPTION
                "Table index of the running Inverter modules. "
            ::= { hwInverterModuleSampleEntry 1 }

        hwInverterModuleEquipId OBJECT-TYPE
            SYNTAX Unsigned32
            MAX-ACCESS read-only
            STATUS current
            DESCRIPTION
                "Inverter module ID. "
            ::= { hwInverterModuleSampleEntry 2 }

        hwInverterModuleEquipName OBJECT-TYPE
            SYNTAX OCTET STRING (SIZE (0..63))
            MAX-ACCESS read-only
            STATUS current
            DESCRIPTION
                "Device name of the Inverter module, character string type, is used to specify the Inverter module."
            ::= { hwInverterModuleSampleEntry 3 }

        hwInverterModuleInputDCVoltage OBJECT-TYPE
            SYNTAX Unsigned32 (0..4000)
            MAX-ACCESS read-only
            STATUS current
            DESCRIPTION
                "Input voltage of the Inverter Module. It is a real-time analog parameter. Value range: 0 to 400, unit: V, the value is accurate to one decimal place (.1). If the value is 2147483647(0x7FFFFFFF), it indicates that the value is invalid."
            ::= { hwInverterModuleSampleEntry 4 }

        hwInverterModuleInputDCCurrent OBJECT-TYPE
            SYNTAX Unsigned32 (0..1000)
            MAX-ACCESS read-only
            STATUS current
            DESCRIPTION
                "Input current of the Inverter Module. It is a real-time analog parameter. Value range: 0 to 100, unit: A, the value is accurate to one decimal place (.1). If the value is 2147483647(0x7FFFFFFF), it indicates that the value is invalid."
            ::= { hwInverterModuleSampleEntry 5 }

        hwInverterModuleInputDCPower OBJECT-TYPE
            SYNTAX Unsigned32 (0..4000)
            MAX-ACCESS read-only
            STATUS current
            DESCRIPTION
                "Input power of the Inverter Module. It is a real-time analog parameter. Value range: 0 to 40, unit: kW, the value is accurate to two decimal place (.01). If the value is 2147483647(0x7FFFFFFF), it indicates that the value is invalid."
            ::= { hwInverterModuleSampleEntry 6 }

        hwInverterModuleOutputVoltage OBJECT-TYPE
            SYNTAX Unsigned32 (0..3000)
            MAX-ACCESS read-only
            STATUS current
            DESCRIPTION
                "Output voltage of the Inverter Module. It is a real-time analog parameter. Value range: 0 to 300, unit: V, the value is accurate to one decimal place (.1). If the value is 2147483647(0x7FFFFFFF), it indicates that the value is invalid."
            ::= { hwInverterModuleSampleEntry 7 }

        hwInverterModuleOutputCurrent OBJECT-TYPE
            SYNTAX Unsigned32 (0..1000)
            MAX-ACCESS read-only
            STATUS current
            DESCRIPTION
                "Output current of the Inverter Module. It is a real-time analog parameter. Value range: 0 to 100, unit: A, the value is accurate to one decimal place (.1). If the value is 2147483647(0x7FFFFFFF), it indicates that the value is invalid."
            ::= { hwInverterModuleSampleEntry 8 }

        hwInverterModuleOutputFreqency OBJECT-TYPE
            SYNTAX Unsigned32 (0..1000)
            MAX-ACCESS read-only
            STATUS current
            DESCRIPTION
                "Output frequency of the Inverter Module. It is a real-time analog parameter. Value range: 0 to 100, unit: Hz, the value is accurate to one decimal place (.1). If the value is 2147483647(0x7FFFFFFF), it indicates that the value is invalid."
            ::= { hwInverterModuleSampleEntry 9 }

        hwInverterModuleOutputActivePower OBJECT-TYPE
            SYNTAX Unsigned32 (0..4000)
            MAX-ACCESS read-only
            STATUS current
            DESCRIPTION
                "Active power of the Inverter Module. It is a real-time analog parameter. Value range: 0 to 40, unit: kW, the value is accurate to two decimal place (.01). If the value is 2147483647(0x7FFFFFFF), it indicates that the value is invalid."
            ::= { hwInverterModuleSampleEntry 10 }

        hwInverterModuleOutputApparentPower OBJECT-TYPE
            SYNTAX Unsigned32 (0..4000)
            MAX-ACCESS read-only
            STATUS current
            DESCRIPTION
                "Apparent power of the Inverter Module. It is a real-time analog parameter. Value range: 0 to 40, unit: kVA, the value is accurate to two decimal place (.01). If the value is 2147483647(0x7FFFFFFF), it indicates that the value is invalid."
            ::= { hwInverterModuleSampleEntry 11 }

        hwInverterModuleOutputPowerFactor OBJECT-TYPE
            SYNTAX Integer32 (-1000..1000)
            MAX-ACCESS read-only
            STATUS current
            DESCRIPTION
                "Power factor of the Inverter Module. It is a real-time analog parameter. Value range: -1 to 1, unit: NA, the value is accurate to three decimal place (.001). If the value is 2147483647(0x7FFFFFFF), it indicates that the value is invalid."
            ::= { hwInverterModuleSampleEntry 12 }

        hwInverterModuleTemperature OBJECT-TYPE
            SYNTAX Integer32 ( -600..1000)
            MAX-ACCESS read-only
            STATUS current
            DESCRIPTION
                "Temperature of the Inverter Module. It is a real-time analog parameter. Value range: -60 to 100, unit: degC, the value is accurate to one decimal place (.1). If the value is 2147483647(0x7FFFFFFF), it indicates that the value is invalid."
            ::= { hwInverterModuleSampleEntry 14 }

        hwInverterModuleWorkState OBJECT-TYPE
            SYNTAX INTEGER
                {
                off(1),
                vlimbing(2),
                selfcheck(3),
                on(4),
                unknown(255)
                }
            MAX-ACCESS read-only
            STATUS current
            DESCRIPTION
                "Work state of the Inverter module. It is an enumeration type:
                If the enumeration value is 1, it indicates Off; 
                If the enumeration value is 2, it indicates Climbing; 
                If the enumeration value is 3, it indicates Self check; 
                If the enumeration value is 4, it indicates On."
            ::= { hwInverterModuleSampleEntry 15 }

        hwInverterModuleTotalRunTime OBJECT-TYPE
            SYNTAX Unsigned32 (0..65535)
            MAX-ACCESS read-only
            STATUS current
            DESCRIPTION
                "Total run time of the Inverter Module. It is a real-time analog parameter. Value range: 0 to 65535, unit: h, its value is an integer (1). If the value is 2147483647(0x7FFFFFFF), it indicates that the value is invalid."
            ::= { hwInverterModuleSampleEntry 16 }

        hwInverterModuleRatedOutputPower OBJECT-TYPE
            SYNTAX Unsigned32 (0..260)
            MAX-ACCESS read-only
            STATUS current
            DESCRIPTION
                "Rated output power of the Inverter Module. It is a real-time analog parameter. Value range: 0 to 26, unit: kVA, the value is accurate to one decimal place (.1). If the value is 2147483647(0x7FFFFFFF), it indicates that the value is invalid."
            ::= { hwInverterModuleSampleEntry 17 }

        hwInverterModuleRatedOutputVoltage OBJECT-TYPE
            SYNTAX Unsigned32 (0..300)
            MAX-ACCESS read-only
            STATUS current
            DESCRIPTION
                "Rated output voltage of the Inverter module.
                Its value range: 0 to 300, 
                unit: V, 
                and its value is an integer (1).  
                If the value is 2147483647(0x7FFFFFFF), it indicates that the value is invalid."
            ::= { hwInverterModuleSampleEntry 18 }

        hwInverterModuleRatedOutputFrequency OBJECT-TYPE
            SYNTAX Unsigned32 (0..100)
            MAX-ACCESS read-only
            STATUS current
            DESCRIPTION
                "Rated output frequency of the Inverter module. 
                Its value range: 0 to 100, 
                unit: Hz, 
                and its value is an integer (1).  
                If the value is 2147483647(0x7FFFFFFF), it indicates that the value is invalid."
            ::= { hwInverterModuleSampleEntry 19 }

        hwInverterModuleRatedInputVoltage OBJECT-TYPE
            SYNTAX Unsigned32 (0..400)
            MAX-ACCESS read-only
            STATUS current
            DESCRIPTION
                "Rated Input voltage of the Inverter Module. It is a real-time analog parameter. Value range: 0 to 400, unit: V, the value is  an integer (1). If the value is 2147483647(0x7FFFFFFF), it indicates that the value is invalid."
            ::= { hwInverterModuleSampleEntry 20 }

        hwInverterModuleBarcode OBJECT-TYPE
            SYNTAX OCTET STRING (SIZE (0..63))
            MAX-ACCESS read-only
            STATUS current
            DESCRIPTION
                "Barcode of the Inverter Module. "
            ::= { hwInverterModuleSampleEntry 21 }

        hwInverterModuleSoftwareVersion OBJECT-TYPE
            SYNTAX OCTET STRING (SIZE (0..63))
            MAX-ACCESS read-only
            STATUS current
            DESCRIPTION
                "Software version of the Inverter Module. "
            ::= { hwInverterModuleSampleEntry 22 }

        hwInverterModuleHardwareVersion OBJECT-TYPE
            SYNTAX OCTET STRING (SIZE (0..63))
            MAX-ACCESS read-only
            STATUS current
            DESCRIPTION
                "Hardware version of the Inverter Module. "
            ::= { hwInverterModuleSampleEntry 23 }

        hwInverterModuleDeviceAddress OBJECT-TYPE
            SYNTAX Unsigned32 (0..65535)
            MAX-ACCESS read-only
            STATUS current
            DESCRIPTION
                "Device address of the Inverter Module. Value range: 0 to 65535. unit:NA."
            ::= { hwInverterModuleSampleEntry 24 }

        hwInverterModuleFatherEquipName OBJECT-TYPE
            SYNTAX OCTET STRING (SIZE (0..63))
            MAX-ACCESS read-only
            STATUS current
            DESCRIPTION
                "Name of the parent device of the inverter module."
            ::= { hwInverterModuleSampleEntry 25 }

        hwHWInverterModulePhaseInfo OBJECT-TYPE
            SYNTAX INTEGER
                {
                l1(1),
                l2(2),
                l3(3),
                unknown(255)
                }
            MAX-ACCESS read-only
            STATUS current
            DESCRIPTION
                "Pahse info of the Inverter module. It is an enumeration type:
                If the enumeration value is 1, it indicates L1; 
                If the enumeration value is 2, it indicate L2; 
                If the enumeration value is 3, it indicates L3; "
            ::= { hwInverterModuleSampleEntry 26 }

        hwHWInverterModuleSetTable OBJECT-TYPE
            SYNTAX SEQUENCE OF HwHWInverterModuleSetEntry
            MAX-ACCESS not-accessible
             STATUS current
             DESCRIPTION
                "/"
            ::= { hwHWInverter 2 }

        hwHWInverterModuleSetEntry OBJECT-TYPE
                        SYNTAX HwHWInverterModuleSetEntry
            MAX-ACCESS not-accessible
             STATUS current
             DESCRIPTION
                "/"
            INDEX { hwInverterModuleReset }
            ::= { hwHWInverterModuleSetTable 1 }

        HwHWInverterModuleSetEntry            ::= SEQUENCE {
                hwInverterModuleReset
                    INTEGER,
                hwInverterModuleOnOffControl
                    INTEGER
            }

        hwInverterModuleReset OBJECT-TYPE
            SYNTAX INTEGER
                {
                reset(1)
                }
            MAX-ACCESS read-write
            STATUS current
            DESCRIPTION
                "Reset of the Invewrter module. It is an enumeration type:
                If the enumeration value is 1, it indicates reseting module."
            ::= { hwHWInverterModuleSetEntry 1 }

        hwInverterModuleOnOffControl OBJECT-TYPE
            SYNTAX INTEGER
                {
                on(1),
                off(2),
                nulloper(255)
                }
            MAX-ACCESS read-write
            STATUS current
            DESCRIPTION
                "Power-on or power-off of the inverter module. It is an enumeration value:
                If the NMS notifies the SNMP agent that this node is set to 1, it indicates power-on of the inverter module;
                If the NMS notifies the SNMP agent that this node is set to 2, it indicates power-off of the inverter module.
                If the NMS notifies the SNMP agent that this node is set to 255, it indicates nullOper of the inverter module."
            ::= { hwHWInverterModuleSetEntry 2 }

        hwHWBypassModule OBJECT IDENTIFIER ::= { hwSiteHWInverter 4 }

        hwHWBypassModuleSampleTable OBJECT-TYPE
            SYNTAX SEQUENCE OF HwHWBypassModuleSampleEntry
            MAX-ACCESS not-accessible
             STATUS current
             DESCRIPTION
                "/"
            ::= { hwHWBypassModule 1 }

        hwHWBypassModuleSampleEntry OBJECT-TYPE
                        SYNTAX HwHWBypassModuleSampleEntry
            MAX-ACCESS not-accessible
             STATUS current
             DESCRIPTION
                "/"
            INDEX { hwBypassModuleSampIndex }
            ::= { hwHWBypassModuleSampleTable 1 }

        HwHWBypassModuleSampleEntry            ::= SEQUENCE {
                hwBypassModuleSampIndex
                    Unsigned32,
                hwBypassModuleEquipId
                    Unsigned32,
                hwBypassModuleEquipName
                    OCTET STRING,
                hwBypassModuleBarcode
                    OCTET STRING,
                hwBypassModuleSoftwareVersion
                    OCTET STRING,
                hwBypassModuleHardwareVersion
                    OCTET STRING,
                hwBypassModuleInputVoltage
                    Unsigned32,
                hwBypassModuleInputVoltageL1
                    Unsigned32,
                hwBypassModuleInputVoltageL2
                    Unsigned32,
                hwBypassModuleInputVoltageL3
                    Unsigned32,
                hwBypassModuleInputFrequency
                    Unsigned32,
                hwBypassModuleTemperature
                    Integer32,
                hwBypassModuleAirInTemperature
                    Integer32,
                hwBypassModuleWorkState
                    INTEGER,
                hwBypassModuleFatherEquipName
                    OCTET STRING
            }

        hwBypassModuleSampIndex OBJECT-TYPE
            SYNTAX Unsigned32
            MAX-ACCESS read-only
            STATUS current
            DESCRIPTION
                "Table index of the running bypass. "
            ::= { hwHWBypassModuleSampleEntry 1 }

        hwBypassModuleEquipId OBJECT-TYPE
            SYNTAX Unsigned32
            MAX-ACCESS read-only
            STATUS current
            DESCRIPTION
                "bypass module ID. "
            ::= { hwHWBypassModuleSampleEntry 2 }

        hwBypassModuleEquipName OBJECT-TYPE
            SYNTAX OCTET STRING (SIZE (0..63))
            MAX-ACCESS read-only
            STATUS current
            DESCRIPTION
                "Device name of the bypass module, character string type, is used to specify the bypass.
                  Otherwise, the configured character can not be any other languages except English."
            ::= { hwHWBypassModuleSampleEntry 3 }

        hwBypassModuleBarcode OBJECT-TYPE
            SYNTAX OCTET STRING (SIZE (0..63))
            MAX-ACCESS read-only
            STATUS current
            DESCRIPTION
                "Barcode of the bypass module. "
            ::= { hwHWBypassModuleSampleEntry 4 }

        hwBypassModuleSoftwareVersion OBJECT-TYPE
            SYNTAX OCTET STRING (SIZE (0..63))
            MAX-ACCESS read-only
            STATUS current
            DESCRIPTION
                "Software version of the bypass module."
            ::= { hwHWBypassModuleSampleEntry 5 }

        hwBypassModuleHardwareVersion OBJECT-TYPE
            SYNTAX OCTET STRING (SIZE (0..63))
            MAX-ACCESS read-only
            STATUS current
            DESCRIPTION
                "Hardware version of the bypass module."
            ::= { hwHWBypassModuleSampleEntry 6 }

        hwBypassModuleInputVoltage OBJECT-TYPE
            SYNTAX Unsigned32 (0..3000)
            MAX-ACCESS read-only
            STATUS current
            DESCRIPTION
                "Input voltage of the bypass module. It is a real-time analog parameter. Value range: 0 to 300, unit: V, the value is accurate to one decimal place (.1). If the value is 2147483647(0x7FFFFFFF), it indicates that the value is invalid."
            ::= { hwHWBypassModuleSampleEntry 7 }

        hwBypassModuleInputVoltageL1 OBJECT-TYPE
            SYNTAX Unsigned32 (0..8000)
            MAX-ACCESS read-only
            STATUS current
            DESCRIPTION
                "Input L1 voltage of the bypass module. It is a real-time analog parameter. Value range: 0 to 800, unit: V, the value is accurate to one decimal place (.1). If the value is 2147483647(0x7FFFFFFF), it indicates that the value is invalid."
            ::= { hwHWBypassModuleSampleEntry 8 }

        hwBypassModuleInputVoltageL2 OBJECT-TYPE
            SYNTAX Unsigned32 (0..8000)
            MAX-ACCESS read-only
            STATUS current
            DESCRIPTION
                "Input L2 voltage of the bypass module. It is a real-time analog parameter. Value range: 0 to 800, unit: V, the value is accurate to one decimal place (.1). If the value is 2147483647(0x7FFFFFFF), it indicates that the value is invalid."
            ::= { hwHWBypassModuleSampleEntry 9 }

        hwBypassModuleInputVoltageL3 OBJECT-TYPE
            SYNTAX Unsigned32 (0..8000)
            MAX-ACCESS read-only
            STATUS current
            DESCRIPTION
                "Input L3 voltage of the bypass module. It is a real-time analog parameter. Value range: 0 to 800, unit: V, the value is accurate to one decimal place (.1). If the value is 2147483647(0x7FFFFFFF), it indicates that the value is invalid."
            ::= { hwHWBypassModuleSampleEntry 10 }

        hwBypassModuleInputFrequency OBJECT-TYPE
            SYNTAX Unsigned32 (0..1000)
            MAX-ACCESS read-only
            STATUS current
            DESCRIPTION
                "Input frequency of the inverter unit. It is a real-time analog parameter. Value range: 0 to 100, unit: Hz, the value is accurate to one decimal place (.1). If the value is 2147483647(0x7FFFFFFF), it indicates that the value is invalid."
            ::= { hwHWBypassModuleSampleEntry 11 }

        hwBypassModuleTemperature OBJECT-TYPE
            SYNTAX Integer32 ( -300..300)
            MAX-ACCESS read-only
            STATUS current
            DESCRIPTION
                "Temperature of the bypass module. It is a real-time analog parameter. Value range: -60 to 100, unit: degC, the value is accurate to one decimal place (.1). If the value is 2147483647(0x7FFFFFFF), it indicates that the value is invalid."
            ::= { hwHWBypassModuleSampleEntry 13 }

        hwBypassModuleAirInTemperature OBJECT-TYPE
            SYNTAX Integer32 ( -300..300)
            MAX-ACCESS read-only
            STATUS current
            DESCRIPTION
                "Air in temperature of the bypass module. It is a real-time analog parameter. Value range: -60 to 100, unit: degC, the value is accurate to one decimal place (.1). If the value is 2147483647(0x7FFFFFFF), it indicates that the value is invalid."
            ::= { hwHWBypassModuleSampleEntry 14 }

        hwBypassModuleWorkState OBJECT-TYPE
            SYNTAX INTEGER
                {
                on(1),
                off(2)
                }
            MAX-ACCESS read-only
            STATUS current
            DESCRIPTION
                "Work state of the bypass module. It is an enumeration type:
                If the enumeration value is 1, it indicates On; 
                If the enumeration value is 2, it indicates Off; "
            ::= { hwHWBypassModuleSampleEntry 15 }

        hwBypassModuleFatherEquipName OBJECT-TYPE
            SYNTAX OCTET STRING (SIZE (0..63))
            MAX-ACCESS read-only
            STATUS current
            DESCRIPTION
                " Father device name of the bypass module equip. "
            ::= { hwHWBypassModuleSampleEntry 16 }

        hwHWBypassModuleSetTable OBJECT-TYPE
            SYNTAX SEQUENCE OF HwHWBypassModuleSetEntry
            MAX-ACCESS not-accessible
             STATUS current
             DESCRIPTION
                "/"
            ::= { hwHWBypassModule 2 }

        hwHWBypassModuleSetEntry OBJECT-TYPE
                        SYNTAX HwHWBypassModuleSetEntry
            MAX-ACCESS not-accessible
             STATUS current
             DESCRIPTION
                "/"
            INDEX { hwBypassModuleInputOverVolt }
            ::= { hwHWBypassModuleSetTable 1 }

        HwHWBypassModuleSetEntry            ::= SEQUENCE {
                hwBypassModuleInputOverVolt
                    INTEGER,
                hwBypassModuleInputUnderVolt
                    INTEGER,
                hwBypassModuleFreqChangeThre
                    Unsigned32
            }

        hwBypassModuleInputOverVolt OBJECT-TYPE
            SYNTAX INTEGER
                {
                percent110(1),
                percent115(2),
                percent120(3)
                }
            MAX-ACCESS read-write
            STATUS current
            DESCRIPTION
                "Input over voltage percent of the bypass module. It is an enumeration type:
                If the enumeration value is 1, it indicates 110%; 
                If the enumeration value is 2, it indicates 115%; 
                If the enumeration value is 3, it indicates 120%; "
            ::= { hwHWBypassModuleSetEntry 1 }

        hwBypassModuleInputUnderVolt OBJECT-TYPE
            SYNTAX INTEGER
                {
                percent90(1),
                percent85(2),
                percent80(3)
                }
            MAX-ACCESS read-write
            STATUS current
            DESCRIPTION
                "Input under voltage percent of the bypass module. It is an enumeration type:
                If the enumeration value is 1, it indicates 90%; 
                If the enumeration value is 2, it indicates 85%; 
                If the enumeration value is 3, it indicates 80%; "
            ::= { hwHWBypassModuleSetEntry 2 }

        hwBypassModuleFreqChangeThre OBJECT-TYPE
            SYNTAX Unsigned32 (1..6)
            MAX-ACCESS read-write
            STATUS current
            DESCRIPTION
                "The bypass module frequency change threshold."
            ::= { hwHWBypassModuleSetEntry 3 }

        hwGeneralEquip OBJECT IDENTIFIER ::= { hwSiteMonitorMIBObjects 45 }

        hwGeneralEquipInfoTable OBJECT-TYPE
            SYNTAX SEQUENCE OF HwGeneralEquipInfoEntry
            MAX-ACCESS not-accessible
             STATUS current
             DESCRIPTION
                "/"
            ::= { hwGeneralEquip 1 }

        hwGeneralEquipInfoEntry OBJECT-TYPE
                        SYNTAX HwGeneralEquipInfoEntry
            MAX-ACCESS not-accessible
             STATUS current
             DESCRIPTION
                "/"
            INDEX { hwGeneralEquipIndex }
            ::= { hwGeneralEquipInfoTable 1 }

        HwGeneralEquipInfoEntry            ::= SEQUENCE {
                hwGeneralEquipIndex
                    Unsigned32,
                hwGeneralEquipId
                    Unsigned32,
                hwGeneralEquipName
                    OCTET STRING,
                hwGeneralEquipFatherEquipName
                    OCTET STRING,
                hwGeneralEquipEquipAddress
                    Unsigned32,
                hwGeneralEquipConnectedPort
                    OCTET STRING,
                hwGeneralEquipRealtimeString1
                    OCTET STRING,
                hwGeneralEquipRealtimeString2
                    OCTET STRING,
                hwGeneralEquipRealtimeString3
                    OCTET STRING,
                hwGeneralEquipRealtimeString4
                    OCTET STRING,
                hwGeneralEquipRealtimeString5
                    OCTET STRING,
                hwGeneralEquipRealtimeString6
                    OCTET STRING,
                hwGeneralEquipRealtimeString7
                    OCTET STRING,
                hwGeneralEquipRealtimeString8
                    OCTET STRING,
                hwGeneralEquipRealtimeString9
                    OCTET STRING,
                hwGeneralEquipRealtimeString10
                    OCTET STRING,
                hwGeneralEquipRealtimeString11
                    OCTET STRING,
                hwGeneralEquipRealtimeString12
                    OCTET STRING,
                hwGeneralEquipRealtimeString13
                    OCTET STRING,
                hwGeneralEquipRealtimeString14
                    OCTET STRING,
                hwGeneralEquipRealtimeString15
                    OCTET STRING,
                hwGeneralEquipRealtimeString16
                    OCTET STRING,
                hwGeneralEquipRealtimeString17
                    OCTET STRING,
                hwGeneralEquipRealtimeString18
                    OCTET STRING,
                hwGeneralEquipRealtimeString19
                    OCTET STRING,
                hwGeneralEquipRealtimeString20
                    OCTET STRING,
                hwGeneralEquipRealtimeString21
                    OCTET STRING,
                hwGeneralEquipRealtimeString22
                    OCTET STRING,
                hwGeneralEquipRealtimeString23
                    OCTET STRING,
                hwGeneralEquipRealtimeString24
                    OCTET STRING,
                hwGeneralEquipRealtimeString25
                    OCTET STRING,
                hwGeneralEquipRealtimeString26
                    OCTET STRING,
                hwGeneralEquipRealtimeString27
                    OCTET STRING,
                hwGeneralEquipRealtimeString28
                    OCTET STRING,
                hwGeneralEquipRealtimeString29
                    OCTET STRING,
                hwGeneralEquipRealtimeString30
                    OCTET STRING,
                hwGeneralEquipRealtimeString31
                    OCTET STRING,
                hwGeneralEquipRealtimeString32
                    OCTET STRING,
                hwGeneralEquipRealtimeString33
                    OCTET STRING,
                hwGeneralEquipRealtimeString34
                    OCTET STRING,
                hwGeneralEquipRealtimeString35
                    OCTET STRING,
                hwGeneralEquipRealtimeString36
                    OCTET STRING,
                hwGeneralEquipRealtimeString37
                    OCTET STRING,
                hwGeneralEquipRealtimeString38
                    OCTET STRING,
                hwGeneralEquipRealtimeString39
                    OCTET STRING,
                hwGeneralEquipRealtimeString40
                    OCTET STRING,
                hwGeneralEquipRealtimeString41
                    OCTET STRING,
                hwGeneralEquipRealtimeString42
                    OCTET STRING,
                hwGeneralEquipRealtimeString43
                    OCTET STRING,
                hwGeneralEquipRealtimeString44
                    OCTET STRING,
                hwGeneralEquipRealtimeString45
                    OCTET STRING,
                hwGeneralEquipRealtimeString46
                    OCTET STRING,
                hwGeneralEquipRealtimeString47
                    OCTET STRING,
                hwGeneralEquipRealtimeString48
                    OCTET STRING,
                hwGeneralEquipRealtimeString49
                    OCTET STRING,
                hwGeneralEquipRealtimeString50
                    OCTET STRING,
                hwGeneralEquipRealtimeString51
                    OCTET STRING,
                hwGeneralEquipRealtimeString52
                    OCTET STRING,
                hwGeneralEquipRealtimeString53
                    OCTET STRING,
                hwGeneralEquipRealtimeString54
                    OCTET STRING,
                hwGeneralEquipRealtimeString55
                    OCTET STRING,
                hwGeneralEquipRealtimeString56
                    OCTET STRING,
                hwGeneralEquipRealtimeString57
                    OCTET STRING,
                hwGeneralEquipRealtimeString58
                    OCTET STRING,
                hwGeneralEquipRealtimeString59
                    OCTET STRING,
                hwGeneralEquipRealtimeString60
                    OCTET STRING,
                hwGeneralEquipRealtimeString61
                    OCTET STRING,
                hwGeneralEquipRealtimeString62
                    OCTET STRING,
                hwGeneralEquipRealtimeString63
                    OCTET STRING,
                hwGeneralEquipRealtimeString64
                    OCTET STRING,
                hwGeneralEquipRealtimeString65
                    OCTET STRING,
                hwGeneralEquipRealtimeString66
                    OCTET STRING,
                hwGeneralEquipRealtimeString67
                    OCTET STRING,
                hwGeneralEquipRealtimeString68
                    OCTET STRING,
                hwGeneralEquipRealtimeString69
                    OCTET STRING,
                hwGeneralEquipRealtimeString70
                    OCTET STRING,
                hwGeneralEquipRealtimeString71
                    OCTET STRING,
                hwGeneralEquipRealtimeString72
                    OCTET STRING,
                hwGeneralEquipRealtimeString73
                    OCTET STRING,
                hwGeneralEquipRealtimeString74
                    OCTET STRING,
                hwGeneralEquipRealtimeString75
                    OCTET STRING,
                hwGeneralEquipRealtimeString76
                    OCTET STRING,
                hwGeneralEquipRealtimeString77
                    OCTET STRING,
                hwGeneralEquipRealtimeString78
                    OCTET STRING,
                hwGeneralEquipRealtimeString79
                    OCTET STRING,
                hwGeneralEquipRealtimeString80
                    OCTET STRING,
                hwGeneralEquipRealtimeString81
                    OCTET STRING,
                hwGeneralEquipRealtimeString82
                    OCTET STRING,
                hwGeneralEquipRealtimeString83
                    OCTET STRING,
                hwGeneralEquipRealtimeString84
                    OCTET STRING,
                hwGeneralEquipRealtimeString85
                    OCTET STRING,
                hwGeneralEquipRealtimeString86
                    OCTET STRING,
                hwGeneralEquipRealtimeString87
                    OCTET STRING,
                hwGeneralEquipRealtimeString88
                    OCTET STRING,
                hwGeneralEquipRealtimeString89
                    OCTET STRING,
                hwGeneralEquipRealtimeString90
                    OCTET STRING,
                hwGeneralEquipRealtimeString91
                    OCTET STRING,
                hwGeneralEquipRealtimeString92
                    OCTET STRING,
                hwGeneralEquipRealtimeString93
                    OCTET STRING,
                hwGeneralEquipRealtimeString94
                    OCTET STRING,
                hwGeneralEquipRealtimeString95
                    OCTET STRING,
                hwGeneralEquipRealtimeString96
                    OCTET STRING,
                hwGeneralEquipRealtimeString97
                    OCTET STRING,
                hwGeneralEquipRealtimeString98
                    OCTET STRING,
                hwGeneralEquipRealtimeString99
                    OCTET STRING,
                hwGeneralEquipRealtimeString100
                    OCTET STRING
            }

        hwGeneralEquipIndex OBJECT-TYPE
            SYNTAX Unsigned32
            MAX-ACCESS read-only
            STATUS current
            DESCRIPTION
                "Table index of the General equipment."
            ::= { hwGeneralEquipInfoEntry 1 }

        hwGeneralEquipId OBJECT-TYPE
            SYNTAX Unsigned32
            MAX-ACCESS read-only
            STATUS current
            DESCRIPTION
                "Device ID of the General equipment."
            ::= { hwGeneralEquipInfoEntry 2 }

        hwGeneralEquipName OBJECT-TYPE
            SYNTAX OCTET STRING (SIZE (0..63))
            MAX-ACCESS read-only
            STATUS current
            DESCRIPTION
                "Device name of the General equipment."
            ::= { hwGeneralEquipInfoEntry 3 }

        hwGeneralEquipFatherEquipName OBJECT-TYPE
            SYNTAX OCTET STRING (SIZE (0..63))
            MAX-ACCESS read-only
            STATUS current
            DESCRIPTION
                "Name of the parent device of the General equipment."
            ::= { hwGeneralEquipInfoEntry 4 }

        hwGeneralEquipEquipAddress OBJECT-TYPE
            SYNTAX Unsigned32 (0..255)
            MAX-ACCESS read-only
            STATUS current
            DESCRIPTION
                "Equip Address of the General equipment."
            ::= { hwGeneralEquipInfoEntry 5 }

        hwGeneralEquipConnectedPort OBJECT-TYPE
            SYNTAX OCTET STRING (SIZE (0..60))
            MAX-ACCESS read-only
            STATUS current
            DESCRIPTION
                "Connected Port  of the General equipment."
            ::= { hwGeneralEquipInfoEntry 6 }

        hwGeneralEquipRealtimeString1 OBJECT-TYPE
            SYNTAX OCTET STRING (SIZE (0..60))
            MAX-ACCESS read-only
            STATUS current
            DESCRIPTION
                "Real time string1 of the general equipment."
            ::= { hwGeneralEquipInfoEntry 7 }

        hwGeneralEquipRealtimeString2 OBJECT-TYPE
            SYNTAX OCTET STRING (SIZE (0..60))
            MAX-ACCESS read-only
            STATUS current
            DESCRIPTION
                "Real time string2 of the general equipment."
            ::= { hwGeneralEquipInfoEntry 8 }

        hwGeneralEquipRealtimeString3 OBJECT-TYPE
            SYNTAX OCTET STRING (SIZE (0..60))
            MAX-ACCESS read-only
            STATUS current
            DESCRIPTION
                "Real time string3 of the general equipment."
            ::= { hwGeneralEquipInfoEntry 9 }

        hwGeneralEquipRealtimeString4 OBJECT-TYPE
            SYNTAX OCTET STRING (SIZE (0..60))
            MAX-ACCESS read-only
            STATUS current
            DESCRIPTION
                "Real time string4 of the general equipment."
            ::= { hwGeneralEquipInfoEntry 10 }

        hwGeneralEquipRealtimeString5 OBJECT-TYPE
            SYNTAX OCTET STRING (SIZE (0..60))
            MAX-ACCESS read-only
            STATUS current
            DESCRIPTION
                "Real time string5 of the general equipment."
            ::= { hwGeneralEquipInfoEntry 11 }

        hwGeneralEquipRealtimeString6 OBJECT-TYPE
            SYNTAX OCTET STRING (SIZE (0..60))
            MAX-ACCESS read-only
            STATUS current
            DESCRIPTION
                "Real time string6 of the general equipment."
            ::= { hwGeneralEquipInfoEntry 12 }

        hwGeneralEquipRealtimeString7 OBJECT-TYPE
            SYNTAX OCTET STRING (SIZE (0..60))
            MAX-ACCESS read-only
            STATUS current
            DESCRIPTION
                "Real time string7 of the general equipment."
            ::= { hwGeneralEquipInfoEntry 13 }

        hwGeneralEquipRealtimeString8 OBJECT-TYPE
            SYNTAX OCTET STRING (SIZE (0..60))
            MAX-ACCESS read-only
            STATUS current
            DESCRIPTION
                "Real time string8 of the general equipment."
            ::= { hwGeneralEquipInfoEntry 14 }

        hwGeneralEquipRealtimeString9 OBJECT-TYPE
            SYNTAX OCTET STRING (SIZE (0..60))
            MAX-ACCESS read-only
            STATUS current
            DESCRIPTION
                "Real time string9 of the general equipment."
            ::= { hwGeneralEquipInfoEntry 15 }

        hwGeneralEquipRealtimeString10 OBJECT-TYPE
            SYNTAX OCTET STRING (SIZE (0..60))
            MAX-ACCESS read-only
            STATUS current
            DESCRIPTION
                "Real time string10 of the general equipment."
            ::= { hwGeneralEquipInfoEntry 16 }

        hwGeneralEquipRealtimeString11 OBJECT-TYPE
            SYNTAX OCTET STRING (SIZE (0..60))
            MAX-ACCESS read-only
            STATUS current
            DESCRIPTION
                "Real time string11 of the general equipment."
            ::= { hwGeneralEquipInfoEntry 17 }

        hwGeneralEquipRealtimeString12 OBJECT-TYPE
            SYNTAX OCTET STRING (SIZE (0..60))
            MAX-ACCESS read-only
            STATUS current
            DESCRIPTION
                "Real time string12 of the general equipment."
            ::= { hwGeneralEquipInfoEntry 18 }

        hwGeneralEquipRealtimeString13 OBJECT-TYPE
            SYNTAX OCTET STRING (SIZE (0..60))
            MAX-ACCESS read-only
            STATUS current
            DESCRIPTION
                "Real time string13 of the general equipment."
            ::= { hwGeneralEquipInfoEntry 19 }

        hwGeneralEquipRealtimeString14 OBJECT-TYPE
            SYNTAX OCTET STRING (SIZE (0..60))
            MAX-ACCESS read-only
            STATUS current
            DESCRIPTION
                "Real time string14 of the general equipment."
            ::= { hwGeneralEquipInfoEntry 20 }

        hwGeneralEquipRealtimeString15 OBJECT-TYPE
            SYNTAX OCTET STRING (SIZE (0..60))
            MAX-ACCESS read-only
            STATUS current
            DESCRIPTION
                "Real time string15 of the general equipment."
            ::= { hwGeneralEquipInfoEntry 21 }

        hwGeneralEquipRealtimeString16 OBJECT-TYPE
            SYNTAX OCTET STRING (SIZE (0..60))
            MAX-ACCESS read-only
            STATUS current
            DESCRIPTION
                "Real time string16 of the general equipment."
            ::= { hwGeneralEquipInfoEntry 22 }

        hwGeneralEquipRealtimeString17 OBJECT-TYPE
            SYNTAX OCTET STRING (SIZE (0..60))
            MAX-ACCESS read-only
            STATUS current
            DESCRIPTION
                "Real time string17 of the general equipment."
            ::= { hwGeneralEquipInfoEntry 23 }

        hwGeneralEquipRealtimeString18 OBJECT-TYPE
            SYNTAX OCTET STRING (SIZE (0..60))
            MAX-ACCESS read-only
            STATUS current
            DESCRIPTION
                "Real time string18 of the general equipment."
            ::= { hwGeneralEquipInfoEntry 24 }

        hwGeneralEquipRealtimeString19 OBJECT-TYPE
            SYNTAX OCTET STRING (SIZE (0..60))
            MAX-ACCESS read-only
            STATUS current
            DESCRIPTION
                "Real time string19 of the general equipment."
            ::= { hwGeneralEquipInfoEntry 25 }

        hwGeneralEquipRealtimeString20 OBJECT-TYPE
            SYNTAX OCTET STRING (SIZE (0..60))
            MAX-ACCESS read-only
            STATUS current
            DESCRIPTION
                "Real time string20 of the general equipment."
            ::= { hwGeneralEquipInfoEntry 26 }

        hwGeneralEquipRealtimeString21 OBJECT-TYPE
            SYNTAX OCTET STRING (SIZE (0..60))
            MAX-ACCESS read-only
            STATUS current
            DESCRIPTION
                "Real time string21 of the general equipment."
            ::= { hwGeneralEquipInfoEntry 27 }

        hwGeneralEquipRealtimeString22 OBJECT-TYPE
            SYNTAX OCTET STRING (SIZE (0..60))
            MAX-ACCESS read-only
            STATUS current
            DESCRIPTION
                "Real time string22 of the general equipment."
            ::= { hwGeneralEquipInfoEntry 28 }

        hwGeneralEquipRealtimeString23 OBJECT-TYPE
            SYNTAX OCTET STRING (SIZE (0..60))
            MAX-ACCESS read-only
            STATUS current
            DESCRIPTION
                "Real time string23 of the general equipment."
            ::= { hwGeneralEquipInfoEntry 29 }

        hwGeneralEquipRealtimeString24 OBJECT-TYPE
            SYNTAX OCTET STRING (SIZE (0..60))
            MAX-ACCESS read-only
            STATUS current
            DESCRIPTION
                "Real time string24 of the general equipment."
            ::= { hwGeneralEquipInfoEntry 30 }

        hwGeneralEquipRealtimeString25 OBJECT-TYPE
            SYNTAX OCTET STRING (SIZE (0..60))
            MAX-ACCESS read-only
            STATUS current
            DESCRIPTION
                "Real time string25 of the general equipment."
            ::= { hwGeneralEquipInfoEntry 31 }

        hwGeneralEquipRealtimeString26 OBJECT-TYPE
            SYNTAX OCTET STRING (SIZE (0..60))
            MAX-ACCESS read-only
            STATUS current
            DESCRIPTION
                "Real time string26 of the general equipment."
            ::= { hwGeneralEquipInfoEntry 32 }

        hwGeneralEquipRealtimeString27 OBJECT-TYPE
            SYNTAX OCTET STRING (SIZE (0..60))
            MAX-ACCESS read-only
            STATUS current
            DESCRIPTION
                "Real time string27 of the general equipment."
            ::= { hwGeneralEquipInfoEntry 33 }

        hwGeneralEquipRealtimeString28 OBJECT-TYPE
            SYNTAX OCTET STRING (SIZE (0..60))
            MAX-ACCESS read-only
            STATUS current
            DESCRIPTION
                "Real time string28 of the general equipment."
            ::= { hwGeneralEquipInfoEntry 34 }

        hwGeneralEquipRealtimeString29 OBJECT-TYPE
            SYNTAX OCTET STRING (SIZE (0..60))
            MAX-ACCESS read-only
            STATUS current
            DESCRIPTION
                "Real time string29 of the general equipment."
            ::= { hwGeneralEquipInfoEntry 35 }

        hwGeneralEquipRealtimeString30 OBJECT-TYPE
            SYNTAX OCTET STRING (SIZE (0..60))
            MAX-ACCESS read-only
            STATUS current
            DESCRIPTION
                "Real time string30 of the general equipment."
            ::= { hwGeneralEquipInfoEntry 36 }

        hwGeneralEquipRealtimeString31 OBJECT-TYPE
            SYNTAX OCTET STRING (SIZE (0..60))
            MAX-ACCESS read-only
            STATUS current
            DESCRIPTION
                "Real time string31 of the general equipment."
            ::= { hwGeneralEquipInfoEntry 37 }

        hwGeneralEquipRealtimeString32 OBJECT-TYPE
            SYNTAX OCTET STRING (SIZE (0..60))
            MAX-ACCESS read-only
            STATUS current
            DESCRIPTION
                "Real time string32 of the general equipment."
            ::= { hwGeneralEquipInfoEntry 38 }

        hwGeneralEquipRealtimeString33 OBJECT-TYPE
            SYNTAX OCTET STRING (SIZE (0..60))
            MAX-ACCESS read-only
            STATUS current
            DESCRIPTION
                "Real time string33 of the general equipment."
            ::= { hwGeneralEquipInfoEntry 39 }

        hwGeneralEquipRealtimeString34 OBJECT-TYPE
            SYNTAX OCTET STRING (SIZE (0..60))
            MAX-ACCESS read-only
            STATUS current
            DESCRIPTION
                "Real time string34 of the general equipment."
            ::= { hwGeneralEquipInfoEntry 40 }

        hwGeneralEquipRealtimeString35 OBJECT-TYPE
            SYNTAX OCTET STRING (SIZE (0..60))
            MAX-ACCESS read-only
            STATUS current
            DESCRIPTION
                "Real time string35 of the general equipment."
            ::= { hwGeneralEquipInfoEntry 41 }

        hwGeneralEquipRealtimeString36 OBJECT-TYPE
            SYNTAX OCTET STRING (SIZE (0..60))
            MAX-ACCESS read-only
            STATUS current
            DESCRIPTION
                "Real time string36 of the general equipment."
            ::= { hwGeneralEquipInfoEntry 42 }

        hwGeneralEquipRealtimeString37 OBJECT-TYPE
            SYNTAX OCTET STRING (SIZE (0..60))
            MAX-ACCESS read-only
            STATUS current
            DESCRIPTION
                "Real time string37 of the general equipment."
            ::= { hwGeneralEquipInfoEntry 43 }

        hwGeneralEquipRealtimeString38 OBJECT-TYPE
            SYNTAX OCTET STRING (SIZE (0..60))
            MAX-ACCESS read-only
            STATUS current
            DESCRIPTION
                "Real time string38 of the general equipment."
            ::= { hwGeneralEquipInfoEntry 44 }

        hwGeneralEquipRealtimeString39 OBJECT-TYPE
            SYNTAX OCTET STRING (SIZE (0..60))
            MAX-ACCESS read-only
            STATUS current
            DESCRIPTION
                "Real time string39 of the general equipment."
            ::= { hwGeneralEquipInfoEntry 45 }

        hwGeneralEquipRealtimeString40 OBJECT-TYPE
            SYNTAX OCTET STRING (SIZE (0..60))
            MAX-ACCESS read-only
            STATUS current
            DESCRIPTION
                "Real time string40 of the general equipment."
            ::= { hwGeneralEquipInfoEntry 46 }

        hwGeneralEquipRealtimeString41 OBJECT-TYPE
            SYNTAX OCTET STRING (SIZE (0..60))
            MAX-ACCESS read-only
            STATUS current
            DESCRIPTION
                "Real time string41 of the general equipment."
            ::= { hwGeneralEquipInfoEntry 47 }

        hwGeneralEquipRealtimeString42 OBJECT-TYPE
            SYNTAX OCTET STRING (SIZE (0..60))
            MAX-ACCESS read-only
            STATUS current
            DESCRIPTION
                "Real time string42 of the general equipment."
            ::= { hwGeneralEquipInfoEntry 48 }

        hwGeneralEquipRealtimeString43 OBJECT-TYPE
            SYNTAX OCTET STRING (SIZE (0..60))
            MAX-ACCESS read-only
            STATUS current
            DESCRIPTION
                "Real time string43 of the general equipment."
            ::= { hwGeneralEquipInfoEntry 49 }

        hwGeneralEquipRealtimeString44 OBJECT-TYPE
            SYNTAX OCTET STRING (SIZE (0..60))
            MAX-ACCESS read-only
            STATUS current
            DESCRIPTION
                "Real time string44 of the general equipment."
            ::= { hwGeneralEquipInfoEntry 50 }

        hwGeneralEquipRealtimeString45 OBJECT-TYPE
            SYNTAX OCTET STRING (SIZE (0..60))
            MAX-ACCESS read-only
            STATUS current
            DESCRIPTION
                "Real time string45 of the general equipment."
            ::= { hwGeneralEquipInfoEntry 51 }

        hwGeneralEquipRealtimeString46 OBJECT-TYPE
            SYNTAX OCTET STRING (SIZE (0..60))
            MAX-ACCESS read-only
            STATUS current
            DESCRIPTION
                "Real time string46 of the general equipment."
            ::= { hwGeneralEquipInfoEntry 52 }

        hwGeneralEquipRealtimeString47 OBJECT-TYPE
            SYNTAX OCTET STRING (SIZE (0..60))
            MAX-ACCESS read-only
            STATUS current
            DESCRIPTION
                "Real time string47 of the general equipment."
            ::= { hwGeneralEquipInfoEntry 53 }

        hwGeneralEquipRealtimeString48 OBJECT-TYPE
            SYNTAX OCTET STRING (SIZE (0..60))
            MAX-ACCESS read-only
            STATUS current
            DESCRIPTION
                "Real time string48 of the general equipment."
            ::= { hwGeneralEquipInfoEntry 54 }

        hwGeneralEquipRealtimeString49 OBJECT-TYPE
            SYNTAX OCTET STRING (SIZE (0..60))
            MAX-ACCESS read-only
            STATUS current
            DESCRIPTION
                "Real time string49 of the general equipment."
            ::= { hwGeneralEquipInfoEntry 55 }

        hwGeneralEquipRealtimeString50 OBJECT-TYPE
            SYNTAX OCTET STRING (SIZE (0..60))
            MAX-ACCESS read-only
            STATUS current
            DESCRIPTION
                "Real time string50 of the general equipment."
            ::= { hwGeneralEquipInfoEntry 56 }

        hwGeneralEquipRealtimeString51 OBJECT-TYPE
            SYNTAX OCTET STRING (SIZE (0..60))
            MAX-ACCESS read-only
            STATUS current
            DESCRIPTION
                "Real time string51 of the general equipment."
            ::= { hwGeneralEquipInfoEntry 57 }

        hwGeneralEquipRealtimeString52 OBJECT-TYPE
            SYNTAX OCTET STRING (SIZE (0..60))
            MAX-ACCESS read-only
            STATUS current
            DESCRIPTION
                "Real time string52 of the general equipment."
            ::= { hwGeneralEquipInfoEntry 58 }

        hwGeneralEquipRealtimeString53 OBJECT-TYPE
            SYNTAX OCTET STRING (SIZE (0..60))
            MAX-ACCESS read-only
            STATUS current
            DESCRIPTION
                "Real time string53 of the general equipment."
            ::= { hwGeneralEquipInfoEntry 59 }

        hwGeneralEquipRealtimeString54 OBJECT-TYPE
            SYNTAX OCTET STRING (SIZE (0..60))
            MAX-ACCESS read-only
            STATUS current
            DESCRIPTION
                "Real time string54 of the general equipment."
            ::= { hwGeneralEquipInfoEntry 60 }

        hwGeneralEquipRealtimeString55 OBJECT-TYPE
            SYNTAX OCTET STRING (SIZE (0..60))
            MAX-ACCESS read-only
            STATUS current
            DESCRIPTION
                "Real time string55 of the general equipment."
            ::= { hwGeneralEquipInfoEntry 61 }

        hwGeneralEquipRealtimeString56 OBJECT-TYPE
            SYNTAX OCTET STRING (SIZE (0..60))
            MAX-ACCESS read-only
            STATUS current
            DESCRIPTION
                "Real time string56 of the general equipment."
            ::= { hwGeneralEquipInfoEntry 62 }

        hwGeneralEquipRealtimeString57 OBJECT-TYPE
            SYNTAX OCTET STRING (SIZE (0..60))
            MAX-ACCESS read-only
            STATUS current
            DESCRIPTION
                "Real time string57 of the general equipment."
            ::= { hwGeneralEquipInfoEntry 63 }

        hwGeneralEquipRealtimeString58 OBJECT-TYPE
            SYNTAX OCTET STRING (SIZE (0..60))
            MAX-ACCESS read-only
            STATUS current
            DESCRIPTION
                "Real time string58 of the general equipment."
            ::= { hwGeneralEquipInfoEntry 64 }

        hwGeneralEquipRealtimeString59 OBJECT-TYPE
            SYNTAX OCTET STRING (SIZE (0..60))
            MAX-ACCESS read-only
            STATUS current
            DESCRIPTION
                "Real time string59 of the general equipment."
            ::= { hwGeneralEquipInfoEntry 65 }

        hwGeneralEquipRealtimeString60 OBJECT-TYPE
            SYNTAX OCTET STRING (SIZE (0..60))
            MAX-ACCESS read-only
            STATUS current
            DESCRIPTION
                "Real time string60 of the general equipment."
            ::= { hwGeneralEquipInfoEntry 66 }

        hwGeneralEquipRealtimeString61 OBJECT-TYPE
            SYNTAX OCTET STRING (SIZE (0..60))
            MAX-ACCESS read-only
            STATUS current
            DESCRIPTION
                "Real time string61 of the general equipment."
            ::= { hwGeneralEquipInfoEntry 67 }

        hwGeneralEquipRealtimeString62 OBJECT-TYPE
            SYNTAX OCTET STRING (SIZE (0..60))
            MAX-ACCESS read-only
            STATUS current
            DESCRIPTION
                "Real time string62 of the general equipment."
            ::= { hwGeneralEquipInfoEntry 68 }

        hwGeneralEquipRealtimeString63 OBJECT-TYPE
            SYNTAX OCTET STRING (SIZE (0..60))
            MAX-ACCESS read-only
            STATUS current
            DESCRIPTION
                "Real time string63 of the general equipment."
            ::= { hwGeneralEquipInfoEntry 69 }

        hwGeneralEquipRealtimeString64 OBJECT-TYPE
            SYNTAX OCTET STRING (SIZE (0..60))
            MAX-ACCESS read-only
            STATUS current
            DESCRIPTION
                "Real time string64 of the general equipment."
            ::= { hwGeneralEquipInfoEntry 70 }

        hwGeneralEquipRealtimeString65 OBJECT-TYPE
            SYNTAX OCTET STRING (SIZE (0..60))
            MAX-ACCESS read-only
            STATUS current
            DESCRIPTION
                "Real time string65 of the general equipment."
            ::= { hwGeneralEquipInfoEntry 71 }

        hwGeneralEquipRealtimeString66 OBJECT-TYPE
            SYNTAX OCTET STRING (SIZE (0..60))
            MAX-ACCESS read-only
            STATUS current
            DESCRIPTION
                "Real time string66 of the general equipment."
            ::= { hwGeneralEquipInfoEntry 72 }

        hwGeneralEquipRealtimeString67 OBJECT-TYPE
            SYNTAX OCTET STRING (SIZE (0..60))
            MAX-ACCESS read-only
            STATUS current
            DESCRIPTION
                "Real time string67 of the general equipment."
            ::= { hwGeneralEquipInfoEntry 73 }

        hwGeneralEquipRealtimeString68 OBJECT-TYPE
            SYNTAX OCTET STRING (SIZE (0..60))
            MAX-ACCESS read-only
            STATUS current
            DESCRIPTION
                "Real time string68 of the general equipment."
            ::= { hwGeneralEquipInfoEntry 74 }

        hwGeneralEquipRealtimeString69 OBJECT-TYPE
            SYNTAX OCTET STRING (SIZE (0..60))
            MAX-ACCESS read-only
            STATUS current
            DESCRIPTION
                "Real time string69 of the general equipment."
            ::= { hwGeneralEquipInfoEntry 75 }

        hwGeneralEquipRealtimeString70 OBJECT-TYPE
            SYNTAX OCTET STRING (SIZE (0..60))
            MAX-ACCESS read-only
            STATUS current
            DESCRIPTION
                "Real time string70 of the general equipment."
            ::= { hwGeneralEquipInfoEntry 76 }

        hwGeneralEquipRealtimeString71 OBJECT-TYPE
            SYNTAX OCTET STRING (SIZE (0..60))
            MAX-ACCESS read-only
            STATUS current
            DESCRIPTION
                "Real time string71 of the general equipment."
            ::= { hwGeneralEquipInfoEntry 77 }

        hwGeneralEquipRealtimeString72 OBJECT-TYPE
            SYNTAX OCTET STRING (SIZE (0..60))
            MAX-ACCESS read-only
            STATUS current
            DESCRIPTION
                "Real time string72 of the general equipment."
            ::= { hwGeneralEquipInfoEntry 78 }

        hwGeneralEquipRealtimeString73 OBJECT-TYPE
            SYNTAX OCTET STRING (SIZE (0..60))
            MAX-ACCESS read-only
            STATUS current
            DESCRIPTION
                "Real time string73 of the general equipment."
            ::= { hwGeneralEquipInfoEntry 79 }

        hwGeneralEquipRealtimeString74 OBJECT-TYPE
            SYNTAX OCTET STRING (SIZE (0..60))
            MAX-ACCESS read-only
            STATUS current
            DESCRIPTION
                "Real time string74 of the general equipment."
            ::= { hwGeneralEquipInfoEntry 80 }

        hwGeneralEquipRealtimeString75 OBJECT-TYPE
            SYNTAX OCTET STRING (SIZE (0..60))
            MAX-ACCESS read-only
            STATUS current
            DESCRIPTION
                "Real time string75 of the general equipment."
            ::= { hwGeneralEquipInfoEntry 81 }

        hwGeneralEquipRealtimeString76 OBJECT-TYPE
            SYNTAX OCTET STRING (SIZE (0..60))
            MAX-ACCESS read-only
            STATUS current
            DESCRIPTION
                "Real time string76 of the general equipment."
            ::= { hwGeneralEquipInfoEntry 82 }

        hwGeneralEquipRealtimeString77 OBJECT-TYPE
            SYNTAX OCTET STRING (SIZE (0..60))
            MAX-ACCESS read-only
            STATUS current
            DESCRIPTION
                "Real time string77 of the general equipment."
            ::= { hwGeneralEquipInfoEntry 83 }

        hwGeneralEquipRealtimeString78 OBJECT-TYPE
            SYNTAX OCTET STRING (SIZE (0..60))
            MAX-ACCESS read-only
            STATUS current
            DESCRIPTION
                "Real time string78 of the general equipment."
            ::= { hwGeneralEquipInfoEntry 84 }

        hwGeneralEquipRealtimeString79 OBJECT-TYPE
            SYNTAX OCTET STRING (SIZE (0..60))
            MAX-ACCESS read-only
            STATUS current
            DESCRIPTION
                "Real time string79 of the general equipment."
            ::= { hwGeneralEquipInfoEntry 85 }

        hwGeneralEquipRealtimeString80 OBJECT-TYPE
            SYNTAX OCTET STRING (SIZE (0..60))
            MAX-ACCESS read-only
            STATUS current
            DESCRIPTION
                "Real time string80 of the general equipment."
            ::= { hwGeneralEquipInfoEntry 86 }

        hwGeneralEquipRealtimeString81 OBJECT-TYPE
            SYNTAX OCTET STRING (SIZE (0..60))
            MAX-ACCESS read-only
            STATUS current
            DESCRIPTION
                "Real time string81 of the general equipment."
            ::= { hwGeneralEquipInfoEntry 87 }

        hwGeneralEquipRealtimeString82 OBJECT-TYPE
            SYNTAX OCTET STRING (SIZE (0..60))
            MAX-ACCESS read-only
            STATUS current
            DESCRIPTION
                "Real time string82 of the general equipment."
            ::= { hwGeneralEquipInfoEntry 88 }

        hwGeneralEquipRealtimeString83 OBJECT-TYPE
            SYNTAX OCTET STRING (SIZE (0..60))
            MAX-ACCESS read-only
            STATUS current
            DESCRIPTION
                "Real time string83 of the general equipment."
            ::= { hwGeneralEquipInfoEntry 89 }

        hwGeneralEquipRealtimeString84 OBJECT-TYPE
            SYNTAX OCTET STRING (SIZE (0..60))
            MAX-ACCESS read-only
            STATUS current
            DESCRIPTION
                "Real time string84 of the general equipment."
            ::= { hwGeneralEquipInfoEntry 90 }

        hwGeneralEquipRealtimeString85 OBJECT-TYPE
            SYNTAX OCTET STRING (SIZE (0..60))
            MAX-ACCESS read-only
            STATUS current
            DESCRIPTION
                "Real time string85 of the general equipment."
            ::= { hwGeneralEquipInfoEntry 91 }

        hwGeneralEquipRealtimeString86 OBJECT-TYPE
            SYNTAX OCTET STRING (SIZE (0..60))
            MAX-ACCESS read-only
            STATUS current
            DESCRIPTION
                "Real time string86 of the general equipment."
            ::= { hwGeneralEquipInfoEntry 92 }

        hwGeneralEquipRealtimeString87 OBJECT-TYPE
            SYNTAX OCTET STRING (SIZE (0..60))
            MAX-ACCESS read-only
            STATUS current
            DESCRIPTION
                "Real time string87 of the general equipment."
            ::= { hwGeneralEquipInfoEntry 93 }

        hwGeneralEquipRealtimeString88 OBJECT-TYPE
            SYNTAX OCTET STRING (SIZE (0..60))
            MAX-ACCESS read-only
            STATUS current
            DESCRIPTION
                "Real time string88 of the general equipment."
            ::= { hwGeneralEquipInfoEntry 94 }

        hwGeneralEquipRealtimeString89 OBJECT-TYPE
            SYNTAX OCTET STRING (SIZE (0..60))
            MAX-ACCESS read-only
            STATUS current
            DESCRIPTION
                "Real time string89 of the general equipment."
            ::= { hwGeneralEquipInfoEntry 95 }

        hwGeneralEquipRealtimeString90 OBJECT-TYPE
            SYNTAX OCTET STRING (SIZE (0..60))
            MAX-ACCESS read-only
            STATUS current
            DESCRIPTION
                "Real time string90 of the general equipment."
            ::= { hwGeneralEquipInfoEntry 96 }

        hwGeneralEquipRealtimeString91 OBJECT-TYPE
            SYNTAX OCTET STRING (SIZE (0..60))
            MAX-ACCESS read-only
            STATUS current
            DESCRIPTION
                "Real time string91 of the general equipment."
            ::= { hwGeneralEquipInfoEntry 97 }

        hwGeneralEquipRealtimeString92 OBJECT-TYPE
            SYNTAX OCTET STRING (SIZE (0..60))
            MAX-ACCESS read-only
            STATUS current
            DESCRIPTION
                "Real time string92 of the general equipment."
            ::= { hwGeneralEquipInfoEntry 98 }

        hwGeneralEquipRealtimeString93 OBJECT-TYPE
            SYNTAX OCTET STRING (SIZE (0..60))
            MAX-ACCESS read-only
            STATUS current
            DESCRIPTION
                "Real time string93 of the general equipment."
            ::= { hwGeneralEquipInfoEntry 99 }

        hwGeneralEquipRealtimeString94 OBJECT-TYPE
            SYNTAX OCTET STRING (SIZE (0..60))
            MAX-ACCESS read-only
            STATUS current
            DESCRIPTION
                "Real time string94 of the general equipment."
            ::= { hwGeneralEquipInfoEntry 100 }

        hwGeneralEquipRealtimeString95 OBJECT-TYPE
            SYNTAX OCTET STRING (SIZE (0..60))
            MAX-ACCESS read-only
            STATUS current
            DESCRIPTION
                "Real time string95 of the general equipment."
            ::= { hwGeneralEquipInfoEntry 101 }

        hwGeneralEquipRealtimeString96 OBJECT-TYPE
            SYNTAX OCTET STRING (SIZE (0..60))
            MAX-ACCESS read-only
            STATUS current
            DESCRIPTION
                "Real time string96 of the general equipment."
            ::= { hwGeneralEquipInfoEntry 102 }

        hwGeneralEquipRealtimeString97 OBJECT-TYPE
            SYNTAX OCTET STRING (SIZE (0..60))
            MAX-ACCESS read-only
            STATUS current
            DESCRIPTION
                "Real time string97 of the general equipment."
            ::= { hwGeneralEquipInfoEntry 103 }

        hwGeneralEquipRealtimeString98 OBJECT-TYPE
            SYNTAX OCTET STRING (SIZE (0..60))
            MAX-ACCESS read-only
            STATUS current
            DESCRIPTION
                "Real time string98 of the general equipment."
            ::= { hwGeneralEquipInfoEntry 104 }

        hwGeneralEquipRealtimeString99 OBJECT-TYPE
            SYNTAX OCTET STRING (SIZE (0..60))
            MAX-ACCESS read-only
            STATUS current
            DESCRIPTION
                "Real time string99 of the general equipment."
            ::= { hwGeneralEquipInfoEntry 105 }

        hwGeneralEquipRealtimeString100 OBJECT-TYPE
            SYNTAX OCTET STRING (SIZE (0..60))
            MAX-ACCESS read-only
            STATUS current
            DESCRIPTION
                "Real time string100 of the general equipment."
            ::= { hwGeneralEquipInfoEntry 106 }

        hwGeneralEquipSetTable OBJECT-TYPE
            SYNTAX SEQUENCE OF HwGeneralEquipSetEntry
            MAX-ACCESS not-accessible
             STATUS current
             DESCRIPTION
                "/"
            ::= { hwGeneralEquip 2 }

        hwGeneralEquipSetEntry OBJECT-TYPE
                        SYNTAX HwGeneralEquipSetEntry
            MAX-ACCESS not-accessible
             STATUS current
             DESCRIPTION
                "/"
            INDEX { hwGeneralEquipUnsignedIntegerSetting1 }
            ::= { hwGeneralEquipSetTable 1 }

        HwGeneralEquipSetEntry            ::= SEQUENCE {
                hwGeneralEquipUnsignedIntegerSetting1
                    Unsigned32,
                hwGeneralEquipUnsignedIntegerSetting2
                    Unsigned32,
                hwGeneralEquipUnsignedIntegerSetting3
                    Unsigned32,
                hwGeneralEquipUnsignedIntegerSetting4
                    Unsigned32,
                hwGeneralEquipUnsignedIntegerSetting5
                    Unsigned32,
                hwGeneralEquipUnsignedIntegerSetting6
                    Unsigned32,
                hwGeneralEquipUnsignedIntegerSetting7
                    Unsigned32,
                hwGeneralEquipUnsignedIntegerSetting8
                    Unsigned32,
                hwGeneralEquipUnsignedIntegerSetting9
                    Unsigned32,
                hwGeneralEquipUnsignedIntegerSetting10
                    Unsigned32,
                hwGeneralEquipUnsignedIntegerSetting11
                    Unsigned32,
                hwGeneralEquipUnsignedIntegerSetting12
                    Unsigned32,
                hwGeneralEquipUnsignedIntegerSetting13
                    Unsigned32,
                hwGeneralEquipUnsignedIntegerSetting14
                    Unsigned32,
                hwGeneralEquipUnsignedIntegerSetting15
                    Unsigned32,
                hwGeneralEquipUnsignedIntegerSetting16
                    Unsigned32,
                hwGeneralEquipUnsignedIntegerSetting17
                    Unsigned32,
                hwGeneralEquipUnsignedIntegerSetting18
                    Unsigned32,
                hwGeneralEquipUnsignedIntegerSetting19
                    Unsigned32,
                hwGeneralEquipUnsignedIntegerSetting20
                    Unsigned32,
                hwGeneralEquipIntegerSetting1
                    Integer32,
                hwGeneralEquipIntegerSetting2
                    Integer32,
                hwGeneralEquipIntegerSetting3
                    Integer32,
                hwGeneralEquipIntegerSetting4
                    Integer32,
                hwGeneralEquipIntegerSetting5
                    Integer32,
                hwGeneralEquipIntegerSetting6
                    Integer32,
                hwGeneralEquipIntegerSetting7
                    Integer32,
                hwGeneralEquipIntegerSetting8
                    Integer32,
                hwGeneralEquipIntegerSetting9
                    Integer32,
                hwGeneralEquipIntegerSetting10
                    Integer32,
                hwGeneralEquipIntegerSetting11
                    Integer32,
                hwGeneralEquipIntegerSetting12
                    Integer32,
                hwGeneralEquipIntegerSetting13
                    Integer32,
                hwGeneralEquipIntegerSetting14
                    Integer32,
                hwGeneralEquipIntegerSetting15
                    Integer32,
                hwGeneralEquipIntegerSetting16
                    Integer32,
                hwGeneralEquipIntegerSetting17
                    Integer32,
                hwGeneralEquipIntegerSetting18
                    Integer32,
                hwGeneralEquipIntegerSetting19
                    Integer32,
                hwGeneralEquipIntegerSetting20
                    Integer32,
                hwGeneralEquipFloatSetting1
                    Integer32,
                hwGeneralEquipFloatSetting2
                    Integer32,
                hwGeneralEquipFloatSetting3
                    Integer32,
                hwGeneralEquipFloatSetting4
                    Integer32,
                hwGeneralEquipFloatSetting5
                    Integer32,
                hwGeneralEquipFloatSetting6
                    Integer32,
                hwGeneralEquipFloatSetting7
                    Integer32,
                hwGeneralEquipFloatSetting8
                    Integer32,
                hwGeneralEquipFloatSetting9
                    Integer32,
                hwGeneralEquipFloatSetting10
                    Integer32,
                hwGeneralEquipFloatSetting11
                    Integer32,
                hwGeneralEquipFloatSetting12
                    Integer32,
                hwGeneralEquipFloatSetting13
                    Integer32,
                hwGeneralEquipFloatSetting14
                    Integer32,
                hwGeneralEquipFloatSetting15
                    Integer32,
                hwGeneralEquipFloatSetting16
                    Integer32,
                hwGeneralEquipFloatSetting17
                    Integer32,
                hwGeneralEquipFloatSetting18
                    Integer32,
                hwGeneralEquipFloatSetting19
                    Integer32,
                hwGeneralEquipFloatSetting20
                    Integer32,
                hwGeneralEquipStringSetting1
                    OCTET STRING,
                hwGeneralEquipStringSetting2
                    OCTET STRING,
                hwGeneralEquipStringSetting3
                    OCTET STRING,
                hwGeneralEquipStringSetting4
                    OCTET STRING,
                hwGeneralEquipStringSetting5
                    OCTET STRING,
                hwGeneralEquipStringSetting6
                    OCTET STRING,
                hwGeneralEquipStringSetting7
                    OCTET STRING,
                hwGeneralEquipStringSetting8
                    OCTET STRING,
                hwGeneralEquipStringSetting9
                    OCTET STRING,
                hwGeneralEquipStringSetting10
                    OCTET STRING,
                hwGeneralEquipStringSetting11
                    OCTET STRING,
                hwGeneralEquipStringSetting12
                    OCTET STRING,
                hwGeneralEquipStringSetting13
                    OCTET STRING,
                hwGeneralEquipStringSetting14
                    OCTET STRING,
                hwGeneralEquipStringSetting15
                    OCTET STRING,
                hwGeneralEquipStringSetting16
                    OCTET STRING,
                hwGeneralEquipStringSetting17
                    OCTET STRING,
                hwGeneralEquipStringSetting18
                    OCTET STRING,
                hwGeneralEquipStringSetting19
                    OCTET STRING,
                hwGeneralEquipStringSetting20
                    OCTET STRING,
                hwGeneralEquipControl1
                    INTEGER,
                hwGeneralEquipControl2
                    INTEGER,
                hwGeneralEquipControl3
                    INTEGER,
                hwGeneralEquipControl4
                    INTEGER,
                hwGeneralEquipControl5
                    INTEGER,
                hwGeneralEquipControl6
                    INTEGER,
                hwGeneralEquipControl7
                    INTEGER,
                hwGeneralEquipControl8
                    INTEGER,
                hwGeneralEquipControl9
                    INTEGER,
                hwGeneralEquipControl10
                    INTEGER,
                hwGeneralEquipControl11
                    INTEGER,
                hwGeneralEquipControl12
                    INTEGER,
                hwGeneralEquipControl13
                    INTEGER,
                hwGeneralEquipControl14
                    INTEGER,
                hwGeneralEquipControl15
                    INTEGER,
                hwGeneralEquipControl16
                    INTEGER,
                hwGeneralEquipControl17
                    INTEGER,
                hwGeneralEquipControl18
                    INTEGER,
                hwGeneralEquipControl19
                    INTEGER,
                hwGeneralEquipControl20
                    INTEGER,
                hwGeneralEquipDelCommFailedDev
                    INTEGER
            }

        hwGeneralEquipUnsignedIntegerSetting1 OBJECT-TYPE
            SYNTAX Unsigned32 (0..9999999)
            MAX-ACCESS read-write
            STATUS current
            DESCRIPTION
                "Unsigned Integer Setting1 of the general equipment."
            ::= { hwGeneralEquipSetEntry 1 }

        hwGeneralEquipUnsignedIntegerSetting2 OBJECT-TYPE
            SYNTAX Unsigned32 (0..9999999)
            MAX-ACCESS read-write
            STATUS current
            DESCRIPTION
                "Unsigned Integer Setting2 of the general equipment."
            ::= { hwGeneralEquipSetEntry 2 }

        hwGeneralEquipUnsignedIntegerSetting3 OBJECT-TYPE
            SYNTAX Unsigned32 (0..9999999)
            MAX-ACCESS read-write
            STATUS current
            DESCRIPTION
                "Unsigned Integer Setting3 of the general equipment."
            ::= { hwGeneralEquipSetEntry 3 }

        hwGeneralEquipUnsignedIntegerSetting4 OBJECT-TYPE
            SYNTAX Unsigned32 (0..9999999)
            MAX-ACCESS read-write
            STATUS current
            DESCRIPTION
                "Unsigned Integer Setting4 of the general equipment."
            ::= { hwGeneralEquipSetEntry 4 }

        hwGeneralEquipUnsignedIntegerSetting5 OBJECT-TYPE
            SYNTAX Unsigned32 (0..9999999)
            MAX-ACCESS read-write
            STATUS current
            DESCRIPTION
                "Unsigned Integer Setting5 of the general equipment."
            ::= { hwGeneralEquipSetEntry 5 }

        hwGeneralEquipUnsignedIntegerSetting6 OBJECT-TYPE
            SYNTAX Unsigned32 (0..9999999)
            MAX-ACCESS read-write
            STATUS current
            DESCRIPTION
                "Unsigned Integer Setting6 of the general equipment."
            ::= { hwGeneralEquipSetEntry 6 }

        hwGeneralEquipUnsignedIntegerSetting7 OBJECT-TYPE
            SYNTAX Unsigned32 (0..9999999)
            MAX-ACCESS read-write
            STATUS current
            DESCRIPTION
                "Unsigned Integer Setting7 of the general equipment."
            ::= { hwGeneralEquipSetEntry 7 }

        hwGeneralEquipUnsignedIntegerSetting8 OBJECT-TYPE
            SYNTAX Unsigned32 (0..9999999)
            MAX-ACCESS read-write
            STATUS current
            DESCRIPTION
                "Unsigned Integer Setting8 of the general equipment."
            ::= { hwGeneralEquipSetEntry 8 }

        hwGeneralEquipUnsignedIntegerSetting9 OBJECT-TYPE
            SYNTAX Unsigned32 (0..9999999)
            MAX-ACCESS read-write
            STATUS current
            DESCRIPTION
                "Unsigned Integer Setting9 of the general equipment."
            ::= { hwGeneralEquipSetEntry 9 }

        hwGeneralEquipUnsignedIntegerSetting10 OBJECT-TYPE
            SYNTAX Unsigned32 (0..9999999)
            MAX-ACCESS read-write
            STATUS current
            DESCRIPTION
                "Unsigned Integer Setting10 of the general equipment."
            ::= { hwGeneralEquipSetEntry 10 }

        hwGeneralEquipUnsignedIntegerSetting11 OBJECT-TYPE
            SYNTAX Unsigned32 (0..9999999)
            MAX-ACCESS read-write
            STATUS current
            DESCRIPTION
                "Unsigned Integer Setting11 of the general equipment."
            ::= { hwGeneralEquipSetEntry 11 }

        hwGeneralEquipUnsignedIntegerSetting12 OBJECT-TYPE
            SYNTAX Unsigned32 (0..9999999)
            MAX-ACCESS read-write
            STATUS current
            DESCRIPTION
                "Unsigned Integer Setting12 of the general equipment."
            ::= { hwGeneralEquipSetEntry 12 }

        hwGeneralEquipUnsignedIntegerSetting13 OBJECT-TYPE
            SYNTAX Unsigned32 (0..9999999)
            MAX-ACCESS read-write
            STATUS current
            DESCRIPTION
                "Unsigned Integer Setting13 of the general equipment."
            ::= { hwGeneralEquipSetEntry 13 }

        hwGeneralEquipUnsignedIntegerSetting14 OBJECT-TYPE
            SYNTAX Unsigned32 (0..9999999)
            MAX-ACCESS read-write
            STATUS current
            DESCRIPTION
                "Unsigned Integer Setting14 of the general equipment."
            ::= { hwGeneralEquipSetEntry 14 }

        hwGeneralEquipUnsignedIntegerSetting15 OBJECT-TYPE
            SYNTAX Unsigned32 (0..9999999)
            MAX-ACCESS read-write
            STATUS current
            DESCRIPTION
                "Unsigned Integer Setting15 of the general equipment."
            ::= { hwGeneralEquipSetEntry 15 }

        hwGeneralEquipUnsignedIntegerSetting16 OBJECT-TYPE
            SYNTAX Unsigned32 (0..9999999)
            MAX-ACCESS read-write
            STATUS current
            DESCRIPTION
                "Unsigned Integer Setting16 of the general equipment."
            ::= { hwGeneralEquipSetEntry 16 }

        hwGeneralEquipUnsignedIntegerSetting17 OBJECT-TYPE
            SYNTAX Unsigned32 (0..9999999)
            MAX-ACCESS read-write
            STATUS current
            DESCRIPTION
                "Unsigned Integer Setting17 of the general equipment."
            ::= { hwGeneralEquipSetEntry 17 }

        hwGeneralEquipUnsignedIntegerSetting18 OBJECT-TYPE
            SYNTAX Unsigned32 (0..9999999)
            MAX-ACCESS read-write
            STATUS current
            DESCRIPTION
                "Unsigned Integer Setting18 of the general equipment."
            ::= { hwGeneralEquipSetEntry 18 }

        hwGeneralEquipUnsignedIntegerSetting19 OBJECT-TYPE
            SYNTAX Unsigned32 (0..9999999)
            MAX-ACCESS read-write
            STATUS current
            DESCRIPTION
                "Unsigned Integer Setting19 of the general equipment."
            ::= { hwGeneralEquipSetEntry 19 }

        hwGeneralEquipUnsignedIntegerSetting20 OBJECT-TYPE
            SYNTAX Unsigned32 (0..9999999)
            MAX-ACCESS read-write
            STATUS current
            DESCRIPTION
                "Unsigned Integer Setting20 of the general equipment."
            ::= { hwGeneralEquipSetEntry 20 }

        hwGeneralEquipIntegerSetting1 OBJECT-TYPE
            SYNTAX Integer32 ( -9999999..9999999)
            MAX-ACCESS read-write
            STATUS current
            DESCRIPTION
                "Integer Setting1 of the general equipment."
            ::= { hwGeneralEquipSetEntry 21 }

        hwGeneralEquipIntegerSetting2 OBJECT-TYPE
            SYNTAX Integer32 ( -9999999..9999999)
            MAX-ACCESS read-write
            STATUS current
            DESCRIPTION
                "Integer Setting2 of the general equipment."
            ::= { hwGeneralEquipSetEntry 22 }

        hwGeneralEquipIntegerSetting3 OBJECT-TYPE
            SYNTAX Integer32 ( -9999999..9999999)
            MAX-ACCESS read-write
            STATUS current
            DESCRIPTION
                "Integer Setting3 of the general equipment."
            ::= { hwGeneralEquipSetEntry 23 }

        hwGeneralEquipIntegerSetting4 OBJECT-TYPE
            SYNTAX Integer32 ( -9999999..9999999)
            MAX-ACCESS read-write
            STATUS current
            DESCRIPTION
                "Integer Setting4 of the general equipment."
            ::= { hwGeneralEquipSetEntry 24 }

        hwGeneralEquipIntegerSetting5 OBJECT-TYPE
            SYNTAX Integer32 ( -9999999..9999999)
            MAX-ACCESS read-write
            STATUS current
            DESCRIPTION
                "Integer Setting5 of the general equipment."
            ::= { hwGeneralEquipSetEntry 25 }

        hwGeneralEquipIntegerSetting6 OBJECT-TYPE
            SYNTAX Integer32 ( -9999999..9999999)
            MAX-ACCESS read-write
            STATUS current
            DESCRIPTION
                "Integer Setting6 of the general equipment."
            ::= { hwGeneralEquipSetEntry 26 }

        hwGeneralEquipIntegerSetting7 OBJECT-TYPE
            SYNTAX Integer32 ( -9999999..9999999)
            MAX-ACCESS read-write
            STATUS current
            DESCRIPTION
                "Integer Setting7 of the general equipment."
            ::= { hwGeneralEquipSetEntry 27 }

        hwGeneralEquipIntegerSetting8 OBJECT-TYPE
            SYNTAX Integer32 ( -9999999..9999999)
            MAX-ACCESS read-write
            STATUS current
            DESCRIPTION
                "Integer Setting8 of the general equipment."
            ::= { hwGeneralEquipSetEntry 28 }

        hwGeneralEquipIntegerSetting9 OBJECT-TYPE
            SYNTAX Integer32 ( -9999999..9999999)
            MAX-ACCESS read-write
            STATUS current
            DESCRIPTION
                "Integer Setting9 of the general equipment."
            ::= { hwGeneralEquipSetEntry 29 }

        hwGeneralEquipIntegerSetting10 OBJECT-TYPE
            SYNTAX Integer32 ( -9999999..9999999)
            MAX-ACCESS read-write
            STATUS current
            DESCRIPTION
                "Integer Setting10 of the general equipment."
            ::= { hwGeneralEquipSetEntry 30 }

        hwGeneralEquipIntegerSetting11 OBJECT-TYPE
            SYNTAX Integer32 ( -9999999..9999999)
            MAX-ACCESS read-write
            STATUS current
            DESCRIPTION
                "Integer Setting11 of the general equipment."
            ::= { hwGeneralEquipSetEntry 31 }

        hwGeneralEquipIntegerSetting12 OBJECT-TYPE
            SYNTAX Integer32 ( -9999999..9999999)
            MAX-ACCESS read-write
            STATUS current
            DESCRIPTION
                "Integer Setting12 of the general equipment."
            ::= { hwGeneralEquipSetEntry 32 }

        hwGeneralEquipIntegerSetting13 OBJECT-TYPE
            SYNTAX Integer32 ( -9999999..9999999)
            MAX-ACCESS read-write
            STATUS current
            DESCRIPTION
                "Integer Setting13 of the general equipment."
            ::= { hwGeneralEquipSetEntry 33 }

        hwGeneralEquipIntegerSetting14 OBJECT-TYPE
            SYNTAX Integer32 ( -9999999..9999999)
            MAX-ACCESS read-write
            STATUS current
            DESCRIPTION
                "Integer Setting14 of the general equipment."
            ::= { hwGeneralEquipSetEntry 34 }

        hwGeneralEquipIntegerSetting15 OBJECT-TYPE
            SYNTAX Integer32 ( -9999999..9999999)
            MAX-ACCESS read-write
            STATUS current
            DESCRIPTION
                "Integer Setting15 of the general equipment."
            ::= { hwGeneralEquipSetEntry 35 }

        hwGeneralEquipIntegerSetting16 OBJECT-TYPE
            SYNTAX Integer32 ( -9999999..9999999)
            MAX-ACCESS read-write
            STATUS current
            DESCRIPTION
                "Integer Setting16 of the general equipment."
            ::= { hwGeneralEquipSetEntry 36 }

        hwGeneralEquipIntegerSetting17 OBJECT-TYPE
            SYNTAX Integer32 ( -9999999..9999999)
            MAX-ACCESS read-write
            STATUS current
            DESCRIPTION
                "Integer Setting17 of the general equipment."
            ::= { hwGeneralEquipSetEntry 37 }

        hwGeneralEquipIntegerSetting18 OBJECT-TYPE
            SYNTAX Integer32 ( -9999999..9999999)
            MAX-ACCESS read-write
            STATUS current
            DESCRIPTION
                "Integer Setting18 of the general equipment."
            ::= { hwGeneralEquipSetEntry 38 }

        hwGeneralEquipIntegerSetting19 OBJECT-TYPE
            SYNTAX Integer32 ( -9999999..9999999)
            MAX-ACCESS read-write
            STATUS current
            DESCRIPTION
                "Integer Setting19 of the general equipment."
            ::= { hwGeneralEquipSetEntry 39 }

        hwGeneralEquipIntegerSetting20 OBJECT-TYPE
            SYNTAX Integer32 ( -9999999..9999999)
            MAX-ACCESS read-write
            STATUS current
            DESCRIPTION
                "Integer Setting20 of the general equipment."
            ::= { hwGeneralEquipSetEntry 40 }

        hwGeneralEquipFloatSetting1 OBJECT-TYPE
            SYNTAX Integer32 ( -999999900..999999900)
            MAX-ACCESS read-write
            STATUS current
            DESCRIPTION
                "Float Setting1 of the general equipment."
            ::= { hwGeneralEquipSetEntry 41 }

        hwGeneralEquipFloatSetting2 OBJECT-TYPE
            SYNTAX Integer32 ( -999999900..999999900)
            MAX-ACCESS read-write
            STATUS current
            DESCRIPTION
                "Float Setting2 of the general equipment."
            ::= { hwGeneralEquipSetEntry 42 }

        hwGeneralEquipFloatSetting3 OBJECT-TYPE
            SYNTAX Integer32 ( -999999900..999999900)
            MAX-ACCESS read-write
            STATUS current
            DESCRIPTION
                "Float Setting3 of the general equipment."
            ::= { hwGeneralEquipSetEntry 43 }

        hwGeneralEquipFloatSetting4 OBJECT-TYPE
            SYNTAX Integer32 ( -999999900..999999900)
            MAX-ACCESS read-write
            STATUS current
            DESCRIPTION
                "Float Setting4 of the general equipment."
            ::= { hwGeneralEquipSetEntry 44 }

        hwGeneralEquipFloatSetting5 OBJECT-TYPE
            SYNTAX Integer32 ( -999999900..999999900)
            MAX-ACCESS read-write
            STATUS current
            DESCRIPTION
                "Float Setting5 of the general equipment."
            ::= { hwGeneralEquipSetEntry 45 }

        hwGeneralEquipFloatSetting6 OBJECT-TYPE
            SYNTAX Integer32 ( -999999900..999999900)
            MAX-ACCESS read-write
            STATUS current
            DESCRIPTION
                "Float Setting6 of the general equipment."
            ::= { hwGeneralEquipSetEntry 46 }

        hwGeneralEquipFloatSetting7 OBJECT-TYPE
            SYNTAX Integer32 ( -999999900..999999900)
            MAX-ACCESS read-write
            STATUS current
            DESCRIPTION
                "Float Setting7 of the general equipment."
            ::= { hwGeneralEquipSetEntry 47 }

        hwGeneralEquipFloatSetting8 OBJECT-TYPE
            SYNTAX Integer32 ( -999999900..999999900)
            MAX-ACCESS read-write
            STATUS current
            DESCRIPTION
                "Float Setting8 of the general equipment."
            ::= { hwGeneralEquipSetEntry 48 }

        hwGeneralEquipFloatSetting9 OBJECT-TYPE
            SYNTAX Integer32 ( -999999900..999999900)
            MAX-ACCESS read-write
            STATUS current
            DESCRIPTION
                "Float Setting9 of the general equipment."
            ::= { hwGeneralEquipSetEntry 49 }

        hwGeneralEquipFloatSetting10 OBJECT-TYPE
            SYNTAX Integer32 ( -999999900..999999900)
            MAX-ACCESS read-write
            STATUS current
            DESCRIPTION
                "Float Setting10 of the general equipment."
            ::= { hwGeneralEquipSetEntry 50 }

        hwGeneralEquipFloatSetting11 OBJECT-TYPE
            SYNTAX Integer32 ( -999999900..999999900)
            MAX-ACCESS read-write
            STATUS current
            DESCRIPTION
                "Float Setting11 of the general equipment."
            ::= { hwGeneralEquipSetEntry 51 }

        hwGeneralEquipFloatSetting12 OBJECT-TYPE
            SYNTAX Integer32 ( -999999900..999999900)
            MAX-ACCESS read-write
            STATUS current
            DESCRIPTION
                "Float Setting12 of the general equipment."
            ::= { hwGeneralEquipSetEntry 52 }

        hwGeneralEquipFloatSetting13 OBJECT-TYPE
            SYNTAX Integer32 ( -999999900..999999900)
            MAX-ACCESS read-write
            STATUS current
            DESCRIPTION
                "Float Setting13 of the general equipment."
            ::= { hwGeneralEquipSetEntry 53 }

        hwGeneralEquipFloatSetting14 OBJECT-TYPE
            SYNTAX Integer32 ( -999999900..999999900)
            MAX-ACCESS read-write
            STATUS current
            DESCRIPTION
                "Float Setting14 of the general equipment."
            ::= { hwGeneralEquipSetEntry 54 }

        hwGeneralEquipFloatSetting15 OBJECT-TYPE
            SYNTAX Integer32 ( -999999900..999999900)
            MAX-ACCESS read-write
            STATUS current
            DESCRIPTION
                "Float Setting15 of the general equipment."
            ::= { hwGeneralEquipSetEntry 55 }

        hwGeneralEquipFloatSetting16 OBJECT-TYPE
            SYNTAX Integer32 ( -999999900..999999900)
            MAX-ACCESS read-write
            STATUS current
            DESCRIPTION
                "Float Setting16 of the general equipment."
            ::= { hwGeneralEquipSetEntry 56 }

        hwGeneralEquipFloatSetting17 OBJECT-TYPE
            SYNTAX Integer32 ( -999999900..999999900)
            MAX-ACCESS read-write
            STATUS current
            DESCRIPTION
                "Float Setting17 of the general equipment."
            ::= { hwGeneralEquipSetEntry 57 }

        hwGeneralEquipFloatSetting18 OBJECT-TYPE
            SYNTAX Integer32 ( -999999900..999999900)
            MAX-ACCESS read-write
            STATUS current
            DESCRIPTION
                "Float Setting18 of the general equipment."
            ::= { hwGeneralEquipSetEntry 58 }

        hwGeneralEquipFloatSetting19 OBJECT-TYPE
            SYNTAX Integer32 ( -999999900..999999900)
            MAX-ACCESS read-write
            STATUS current
            DESCRIPTION
                "Float Setting19 of the general equipment."
            ::= { hwGeneralEquipSetEntry 59 }

        hwGeneralEquipFloatSetting20 OBJECT-TYPE
            SYNTAX Integer32 ( -999999900..999999900)
            MAX-ACCESS read-write
            STATUS current
            DESCRIPTION
                "Float Setting20 of the general equipment."
            ::= { hwGeneralEquipSetEntry 60 }

        hwGeneralEquipStringSetting1 OBJECT-TYPE
            SYNTAX OCTET STRING (SIZE (0..60))
            MAX-ACCESS read-write
            STATUS current
            DESCRIPTION
                "String Setting1 of the general equipment."
            ::= { hwGeneralEquipSetEntry 61 }

        hwGeneralEquipStringSetting2 OBJECT-TYPE
            SYNTAX OCTET STRING (SIZE (0..60))
            MAX-ACCESS read-write
            STATUS current
            DESCRIPTION
                "String Setting2 of the general equipment."
            ::= { hwGeneralEquipSetEntry 62 }

        hwGeneralEquipStringSetting3 OBJECT-TYPE
            SYNTAX OCTET STRING (SIZE (0..60))
            MAX-ACCESS read-write
            STATUS current
            DESCRIPTION
                "String Setting3 of the general equipment."
            ::= { hwGeneralEquipSetEntry 63 }

        hwGeneralEquipStringSetting4 OBJECT-TYPE
            SYNTAX OCTET STRING (SIZE (0..60))
            MAX-ACCESS read-write
            STATUS current
            DESCRIPTION
                "String Setting4 of the general equipment."
            ::= { hwGeneralEquipSetEntry 64 }

        hwGeneralEquipStringSetting5 OBJECT-TYPE
            SYNTAX OCTET STRING (SIZE (0..60))
            MAX-ACCESS read-write
            STATUS current
            DESCRIPTION
                "String Setting5 of the general equipment."
            ::= { hwGeneralEquipSetEntry 65 }

        hwGeneralEquipStringSetting6 OBJECT-TYPE
            SYNTAX OCTET STRING (SIZE (0..60))
            MAX-ACCESS read-write
            STATUS current
            DESCRIPTION
                "String Setting6 of the general equipment."
            ::= { hwGeneralEquipSetEntry 66 }

        hwGeneralEquipStringSetting7 OBJECT-TYPE
            SYNTAX OCTET STRING (SIZE (0..60))
            MAX-ACCESS read-write
            STATUS current
            DESCRIPTION
                "String Setting7 of the general equipment."
            ::= { hwGeneralEquipSetEntry 67 }

        hwGeneralEquipStringSetting8 OBJECT-TYPE
            SYNTAX OCTET STRING (SIZE (0..60))
            MAX-ACCESS read-write
            STATUS current
            DESCRIPTION
                "String Setting8 of the general equipment."
            ::= { hwGeneralEquipSetEntry 68 }

        hwGeneralEquipStringSetting9 OBJECT-TYPE
            SYNTAX OCTET STRING (SIZE (0..60))
            MAX-ACCESS read-write
            STATUS current
            DESCRIPTION
                "String Setting9 of the general equipment."
            ::= { hwGeneralEquipSetEntry 69 }

        hwGeneralEquipStringSetting10 OBJECT-TYPE
            SYNTAX OCTET STRING (SIZE (0..60))
            MAX-ACCESS read-write
            STATUS current
            DESCRIPTION
                "String Setting10 of the general equipment."
            ::= { hwGeneralEquipSetEntry 70 }

        hwGeneralEquipStringSetting11 OBJECT-TYPE
            SYNTAX OCTET STRING (SIZE (0..60))
            MAX-ACCESS read-write
            STATUS current
            DESCRIPTION
                "String Setting11 of the general equipment."
            ::= { hwGeneralEquipSetEntry 71 }

        hwGeneralEquipStringSetting12 OBJECT-TYPE
            SYNTAX OCTET STRING (SIZE (0..60))
            MAX-ACCESS read-write
            STATUS current
            DESCRIPTION
                "String Setting12 of the general equipment."
            ::= { hwGeneralEquipSetEntry 72 }

        hwGeneralEquipStringSetting13 OBJECT-TYPE
            SYNTAX OCTET STRING (SIZE (0..60))
            MAX-ACCESS read-write
            STATUS current
            DESCRIPTION
                "String Setting13 of the general equipment."
            ::= { hwGeneralEquipSetEntry 73 }

        hwGeneralEquipStringSetting14 OBJECT-TYPE
            SYNTAX OCTET STRING (SIZE (0..60))
            MAX-ACCESS read-write
            STATUS current
            DESCRIPTION
                "String Setting14 of the general equipment."
            ::= { hwGeneralEquipSetEntry 74 }

        hwGeneralEquipStringSetting15 OBJECT-TYPE
            SYNTAX OCTET STRING (SIZE (0..60))
            MAX-ACCESS read-write
            STATUS current
            DESCRIPTION
                "String Setting15 of the general equipment."
            ::= { hwGeneralEquipSetEntry 75 }

        hwGeneralEquipStringSetting16 OBJECT-TYPE
            SYNTAX OCTET STRING (SIZE (0..60))
            MAX-ACCESS read-write
            STATUS current
            DESCRIPTION
                "String Setting16 of the general equipment."
            ::= { hwGeneralEquipSetEntry 76 }

        hwGeneralEquipStringSetting17 OBJECT-TYPE
            SYNTAX OCTET STRING (SIZE (0..60))
            MAX-ACCESS read-write
            STATUS current
            DESCRIPTION
                "String Setting17 of the general equipment."
            ::= { hwGeneralEquipSetEntry 77 }

        hwGeneralEquipStringSetting18 OBJECT-TYPE
            SYNTAX OCTET STRING (SIZE (0..60))
            MAX-ACCESS read-write
            STATUS current
            DESCRIPTION
                "String Setting18 of the general equipment."
            ::= { hwGeneralEquipSetEntry 78 }

        hwGeneralEquipStringSetting19 OBJECT-TYPE
            SYNTAX OCTET STRING (SIZE (0..60))
            MAX-ACCESS read-write
            STATUS current
            DESCRIPTION
                "String Setting19 of the general equipment."
            ::= { hwGeneralEquipSetEntry 79 }

        hwGeneralEquipStringSetting20 OBJECT-TYPE
            SYNTAX OCTET STRING (SIZE (0..60))
            MAX-ACCESS read-write
            STATUS current
            DESCRIPTION
                "String Setting20 of the general equipment."
            ::= { hwGeneralEquipSetEntry 80 }

        hwGeneralEquipControl1 OBJECT-TYPE
            SYNTAX INTEGER
                {
                yes(1)
                }
            MAX-ACCESS read-write
            STATUS current
            DESCRIPTION
                "Control1 of the general equipment."
            ::= { hwGeneralEquipSetEntry 81 }

        hwGeneralEquipControl2 OBJECT-TYPE
            SYNTAX INTEGER
                {
                yes(1)
                }
            MAX-ACCESS read-write
            STATUS current
            DESCRIPTION
                "Control2 of the general equipment."
            ::= { hwGeneralEquipSetEntry 82 }

        hwGeneralEquipControl3 OBJECT-TYPE
            SYNTAX INTEGER
                {
                yes(1)
                }
            MAX-ACCESS read-write
            STATUS current
            DESCRIPTION
                "Control3 of the general equipment."
            ::= { hwGeneralEquipSetEntry 83 }

        hwGeneralEquipControl4 OBJECT-TYPE
            SYNTAX INTEGER
                {
                yes(1)
                }
            MAX-ACCESS read-write
            STATUS current
            DESCRIPTION
                "Control4 of the general equipment."
            ::= { hwGeneralEquipSetEntry 84 }

        hwGeneralEquipControl5 OBJECT-TYPE
            SYNTAX INTEGER
                {
                yes(1)
                }
            MAX-ACCESS read-write
            STATUS current
            DESCRIPTION
                "Control5 of the general equipment."
            ::= { hwGeneralEquipSetEntry 85 }

        hwGeneralEquipControl6 OBJECT-TYPE
            SYNTAX INTEGER
                {
                yes(1)
                }
            MAX-ACCESS read-write
            STATUS current
            DESCRIPTION
                "Control6 of the general equipment."
            ::= { hwGeneralEquipSetEntry 86 }

        hwGeneralEquipControl7 OBJECT-TYPE
            SYNTAX INTEGER
                {
                yes(1)
                }
            MAX-ACCESS read-write
            STATUS current
            DESCRIPTION
                "Control7 of the general equipment."
            ::= { hwGeneralEquipSetEntry 87 }

        hwGeneralEquipControl8 OBJECT-TYPE
            SYNTAX INTEGER
                {
                yes(1)
                }
            MAX-ACCESS read-write
            STATUS current
            DESCRIPTION
                "Control8 of the general equipment."
            ::= { hwGeneralEquipSetEntry 88 }

        hwGeneralEquipControl9 OBJECT-TYPE
            SYNTAX INTEGER
                {
                yes(1)
                }
            MAX-ACCESS read-write
            STATUS current
            DESCRIPTION
                "Control9 of the general equipment."
            ::= { hwGeneralEquipSetEntry 89 }

        hwGeneralEquipControl10 OBJECT-TYPE
            SYNTAX INTEGER
                {
                yes(1)
                }
            MAX-ACCESS read-write
            STATUS current
            DESCRIPTION
                "Control10 of the general equipment."
            ::= { hwGeneralEquipSetEntry 90 }

        hwGeneralEquipControl11 OBJECT-TYPE
            SYNTAX INTEGER
                {
                yes(1)
                }
            MAX-ACCESS read-write
            STATUS current
            DESCRIPTION
                "Control11 of the general equipment."
            ::= { hwGeneralEquipSetEntry 91 }

        hwGeneralEquipControl12 OBJECT-TYPE
            SYNTAX INTEGER
                {
                yes(1)
                }
            MAX-ACCESS read-write
            STATUS current
            DESCRIPTION
                "Control12 of the general equipment."
            ::= { hwGeneralEquipSetEntry 92 }

        hwGeneralEquipControl13 OBJECT-TYPE
            SYNTAX INTEGER
                {
                yes(1)
                }
            MAX-ACCESS read-write
            STATUS current
            DESCRIPTION
                "Control13 of the general equipment."
            ::= { hwGeneralEquipSetEntry 93 }

        hwGeneralEquipControl14 OBJECT-TYPE
            SYNTAX INTEGER
                {
                yes(1)
                }
            MAX-ACCESS read-write
            STATUS current
            DESCRIPTION
                "Control14 of the general equipment."
            ::= { hwGeneralEquipSetEntry 94 }

        hwGeneralEquipControl15 OBJECT-TYPE
            SYNTAX INTEGER
                {
                yes(1)
                }
            MAX-ACCESS read-write
            STATUS current
            DESCRIPTION
                "Control15 of the general equipment."
            ::= { hwGeneralEquipSetEntry 95 }

        hwGeneralEquipControl16 OBJECT-TYPE
            SYNTAX INTEGER
                {
                yes(1)
                }
            MAX-ACCESS read-write
            STATUS current
            DESCRIPTION
                "Control16 of the general equipment."
            ::= { hwGeneralEquipSetEntry 96 }

        hwGeneralEquipControl17 OBJECT-TYPE
            SYNTAX INTEGER
                {
                yes(1)
                }
            MAX-ACCESS read-write
            STATUS current
            DESCRIPTION
                "Control17 of the general equipment."
            ::= { hwGeneralEquipSetEntry 97 }

        hwGeneralEquipControl18 OBJECT-TYPE
            SYNTAX INTEGER
                {
                yes(1)
                }
            MAX-ACCESS read-write
            STATUS current
            DESCRIPTION
                "Control18 of the general equipment."
            ::= { hwGeneralEquipSetEntry 98 }

        hwGeneralEquipControl19 OBJECT-TYPE
            SYNTAX INTEGER
                {
                yes(1)
                }
            MAX-ACCESS read-write
            STATUS current
            DESCRIPTION
                "Control19 of the general equipment."
            ::= { hwGeneralEquipSetEntry 99 }

        hwGeneralEquipControl20 OBJECT-TYPE
            SYNTAX INTEGER
                {
                yes(1)
                }
            MAX-ACCESS read-write
            STATUS current
            DESCRIPTION
                "Control20 of the general equipment."
            ::= { hwGeneralEquipSetEntry 100 }

        hwGeneralEquipDelCommFailedDev OBJECT-TYPE
            SYNTAX INTEGER
                {
                yes(1)
                }
            MAX-ACCESS read-write
            STATUS current
            DESCRIPTION
                "Delete communication failed device of the general equipment."
            ::= { hwGeneralEquipSetEntry 101 }

        hwSiteDcAmmeter OBJECT IDENTIFIER ::= { hwSiteMonitorMIBObjects 46 }

        hwSiteDcAmmeterEquip OBJECT IDENTIFIER ::= { hwSiteDcAmmeter 1 }

        hwSiteDcAmmeterSampTable OBJECT-TYPE
            SYNTAX SEQUENCE OF HwSiteDcAmmeterSampEntry
            MAX-ACCESS not-accessible
             STATUS current
             DESCRIPTION
                "/"
            ::= { hwSiteDcAmmeterEquip 1 }

        hwSiteDcAmmeterSampEntry OBJECT-TYPE
                        SYNTAX HwSiteDcAmmeterSampEntry
            MAX-ACCESS not-accessible
             STATUS current
             DESCRIPTION
                "/"
            INDEX { hwDcAmmeterIndex }
            ::= { hwSiteDcAmmeterSampTable 1 }

        HwSiteDcAmmeterSampEntry            ::= SEQUENCE {
                hwDcAmmeterIndex
                    Unsigned32,
                hwDcAmmeterEquipId
                    Unsigned32,
                hwDcAmmeterEquipName
                    OCTET STRING,
                hwDcAmmeterChannel1Voltage
                    Unsigned32,
                hwDcAmmeterChannel1Current
                    Integer32,
                hwDcAmmeterChannel1Power
                    Integer32,
                hwDcAmmeterChannel1PowerConsumption
                    Integer32,
                hwDcAmmeterChannel2Voltage
                    Unsigned32,
                hwDcAmmeterChannel2Current
                    Integer32,
                hwDcAmmeterChannel2Power
                    Integer32,
                hwDcAmmeterChannel2PowerConsumption
                    Integer32,
                hwDcAmmeterChannel3Voltage
                    Unsigned32,
                hwDcAmmeterChannel3Current
                    Integer32,
                hwDcAmmeterChannel3Power
                    Integer32,
                hwDcAmmeterChannel3PowerConsumption
                    Integer32,
                hwDcAmmeterChannel4Voltage
                    Unsigned32,
                hwDcAmmeterChannel4Current
                    Integer32,
                hwDcAmmeterChannel4Power
                    Integer32,
                hwDcAmmeterChannel4PowerConsumption
                    Integer32,
                hwDcAmmeterProtocolVersion
                    OCTET STRING,
                hwDcAmmeterSoftwareVersion
                    OCTET STRING,
                hwDcAmmeterHardwareVersion
                    OCTET STRING
            }

        hwDcAmmeterIndex OBJECT-TYPE
            SYNTAX Unsigned32 (4096..20479)
            MAX-ACCESS read-only
            STATUS current
            DESCRIPTION
                "Dc Ammeter table index,which value range:4096to 20479. Lines of the device list are restricted by the quantity of DcAmmeter"
            ::= { hwSiteDcAmmeterSampEntry 1 }

        hwDcAmmeterEquipId OBJECT-TYPE
            SYNTAX Unsigned32
            MAX-ACCESS read-only
            STATUS current
            DESCRIPTION
                "Dc Ammeter device ID. "
            ::= { hwSiteDcAmmeterSampEntry 2 }

        hwDcAmmeterEquipName OBJECT-TYPE
            SYNTAX OCTET STRING (SIZE (0..63))
            MAX-ACCESS read-only
            STATUS current
            DESCRIPTION
                "Dc Ammeter name, of the character string type, is used to specify Dc Ammeter. Users can configure it.
                Otherwise, the configured character can not be any other languages except English."
            ::= { hwSiteDcAmmeterSampEntry 3 }

        hwDcAmmeterChannel1Voltage OBJECT-TYPE
            SYNTAX Unsigned32 (0..10000)
            MAX-ACCESS read-only
            STATUS current
            DESCRIPTION
                "Dc Ammeter channel 1 voltage, 
                Value range: 0.00 to 100.00.
                Unit: V.
                and the value is accurate to two decimal space (.01). 
                If the value is 2147483647(0x7FFFFFFF), it indicates that the value is invalid."
            ::= { hwSiteDcAmmeterSampEntry 4 }

        hwDcAmmeterChannel1Current OBJECT-TYPE
            SYNTAX Integer32 ( -100000..100000)
            MAX-ACCESS read-only
            STATUS current
            DESCRIPTION
                "Dc Ammeter channel 1 current, 
                Value range: -1000.00. to 1000.00.
                Unit: A.
                and the value is accurate to two decimal space (.01). 
                If the value is 2147483647(0x7FFFFFFF), it indicates that the value is invalid."
            ::= { hwSiteDcAmmeterSampEntry 5 }

        hwDcAmmeterChannel1Power OBJECT-TYPE
            SYNTAX Integer32 ( -6000000..6000000)
            MAX-ACCESS read-only
            STATUS current
            DESCRIPTION
                "Dc Ammeter power of channel 1, 
                Value range: -60000.00 to 60000.00.
                Unit: kW.
                and the value is accurate to two decimal space (.01). 
                If the value is 2147483647(0x7FFFFFFF), it indicates that the value is invalid."
            ::= { hwSiteDcAmmeterSampEntry 6 }

        hwDcAmmeterChannel1PowerConsumption OBJECT-TYPE
            SYNTAX Integer32 ( 0..99999999)
            MAX-ACCESS read-only
            STATUS current
            DESCRIPTION
                "Dc Ammeter power consumption of channel 1, 
                Value range: 0 to 999999.99.
                Unit: kWh.
                and the value is accurate to two decimal space (.01). 
                If the value is 2147483647(0x7FFFFFFF), it indicates that the value is invalid."
            ::= { hwSiteDcAmmeterSampEntry 7 }

        hwDcAmmeterChannel2Voltage OBJECT-TYPE
            SYNTAX Unsigned32 (0..10000)
            MAX-ACCESS read-only
            STATUS current
            DESCRIPTION
                "Dc Ammeter channel 2 voltage, 
                Value range: 0.00 to 100.00.
                Unit: V.
                and the value is accurate to two decimal space (.01). 
                If the value is 2147483647(0x7FFFFFFF), it indicates that the value is invalid."
            ::= { hwSiteDcAmmeterSampEntry 8 }

        hwDcAmmeterChannel2Current OBJECT-TYPE
            SYNTAX Integer32 ( -100000..100000)
            MAX-ACCESS read-only
            STATUS current
            DESCRIPTION
                "Dc Ammeter channel 2 current, 
                Value range: -1000.00. to 1000.00.
                Unit: A.
                and the value is accurate to two decimal space (.01). 
                If the value is 2147483647(0x7FFFFFFF), it indicates that the value is invalid."
            ::= { hwSiteDcAmmeterSampEntry 9 }

        hwDcAmmeterChannel2Power OBJECT-TYPE
            SYNTAX Integer32 ( -6000000..6000000)
            MAX-ACCESS read-only
            STATUS current
            DESCRIPTION
                "Dc Ammeter power of channel 2, 
                Value range: -60000.00 to 60000.00.
                Unit: kW.
                and the value is accurate to two decimal space (.01). 
                If the value is 2147483647(0x7FFFFFFF), it indicates that the value is invalid."
            ::= { hwSiteDcAmmeterSampEntry 10 }

        hwDcAmmeterChannel2PowerConsumption OBJECT-TYPE
            SYNTAX Integer32 ( 0..99999999)
            MAX-ACCESS read-only
            STATUS current
            DESCRIPTION
                "Dc Ammeter power consumption of channel 2, 
                Value range: 0 to 999999.99.
                Unit: kWh.
                and the value is accurate to two decimal space (.01). 
                If the value is 2147483647(0x7FFFFFFF), it indicates that the value is invalid."
            ::= { hwSiteDcAmmeterSampEntry 11 }

        hwDcAmmeterChannel3Voltage OBJECT-TYPE
            SYNTAX Unsigned32 (0..10000)
            MAX-ACCESS read-only
            STATUS current
            DESCRIPTION
                "Dc Ammeter channel 3 voltage, 
                Value range: 0.00 to 100.00.
                Unit: V.
                and the value is accurate to two decimal space (.01). 
                If the value is 2147483647(0x7FFFFFFF), it indicates that the value is invalid."
            ::= { hwSiteDcAmmeterSampEntry 12 }

        hwDcAmmeterChannel3Current OBJECT-TYPE
            SYNTAX Integer32 ( -100000..100000)
            MAX-ACCESS read-only
            STATUS current
            DESCRIPTION
                "Dc Ammeter channel 3 current, 
                Value range: -1000.00. to 1000.00.
                Unit: A.
                and the value is accurate to two decimal space (.01). 
                If the value is 2147483647(0x7FFFFFFF), it indicates that the value is invalid."
            ::= { hwSiteDcAmmeterSampEntry 13 }

        hwDcAmmeterChannel3Power OBJECT-TYPE
            SYNTAX Integer32 ( -6000000..6000000)
            MAX-ACCESS read-only
            STATUS current
            DESCRIPTION
                "Dc Ammeter power of channel 3, 
                Value range: -60000.00 to 60000.00.
                Unit: kW.
                and the value is accurate to two decimal space (.01). 
                If the value is 2147483647(0x7FFFFFFF), it indicates that the value is invalid."
            ::= { hwSiteDcAmmeterSampEntry 14 }

        hwDcAmmeterChannel3PowerConsumption OBJECT-TYPE
            SYNTAX Integer32 ( 0..99999999)
            MAX-ACCESS read-only
            STATUS current
            DESCRIPTION
                "Dc Ammeter power consumption of channel 3, 
                Value range: 0 to 999999.99.
                Unit: kWh.
                and the value is accurate to two decimal space (.01). 
                If the value is 2147483647(0x7FFFFFFF), it indicates that the value is invalid."
            ::= { hwSiteDcAmmeterSampEntry 15 }

        hwDcAmmeterChannel4Voltage OBJECT-TYPE
            SYNTAX Unsigned32 (0..10000)
            MAX-ACCESS read-only
            STATUS current
            DESCRIPTION
                "Dc Ammeter channel 4 voltage, 
                Value range: 0.00 to 100.00.
                Unit: V.
                and the value is accurate to two decimal space (.01). 
                If the value is 2147483647(0x7FFFFFFF), it indicates that the value is invalid."
            ::= { hwSiteDcAmmeterSampEntry 16 }

        hwDcAmmeterChannel4Current OBJECT-TYPE
            SYNTAX Integer32 ( -100000..100000)
            MAX-ACCESS read-only
            STATUS current
            DESCRIPTION
                "Dc Ammeter channel 4 current, 
                Value range: -1000.00. to 1000.00.
                Unit: A.
                and the value is accurate to two decimal space (.01). 
                If the value is 2147483647(0x7FFFFFFF), it indicates that the value is invalid."
            ::= { hwSiteDcAmmeterSampEntry 17 }

        hwDcAmmeterChannel4Power OBJECT-TYPE
            SYNTAX Integer32 ( -6000000..6000000)
            MAX-ACCESS read-only
            STATUS current
            DESCRIPTION
                "Dc Ammeter power of channel 4, 
                Value range: -60000.00 to 60000.00.
                Unit: kW.
                and the value is accurate to two decimal space (.01). 
                If the value is 2147483647(0x7FFFFFFF), it indicates that the value is invalid."
            ::= { hwSiteDcAmmeterSampEntry 18 }

        hwDcAmmeterChannel4PowerConsumption OBJECT-TYPE
            SYNTAX Integer32 ( 0..99999999)
            MAX-ACCESS read-only
            STATUS current
            DESCRIPTION
                "Dc Ammeter power consumption of channel 4, 
                Value range: 0 to 999999.99.
                Unit: kWh.
                and the value is accurate to two decimal space (.01). 
                If the value is 2147483647(0x7FFFFFFF), it indicates that the value is invalid."
            ::= { hwSiteDcAmmeterSampEntry 19 }

        hwDcAmmeterProtocolVersion OBJECT-TYPE
            SYNTAX OCTET STRING (SIZE (0..16))
            MAX-ACCESS read-only
            STATUS current
            DESCRIPTION
                "Dc Ammeter protocol version."
            ::= { hwSiteDcAmmeterSampEntry 20 }

        hwDcAmmeterSoftwareVersion OBJECT-TYPE
            SYNTAX OCTET STRING (SIZE (0..16))
            MAX-ACCESS read-only
            STATUS current
            DESCRIPTION
                "Dc Ammeter software verison."
            ::= { hwSiteDcAmmeterSampEntry 21 }

        hwDcAmmeterHardwareVersion OBJECT-TYPE
            SYNTAX OCTET STRING (SIZE (0..16))
            MAX-ACCESS read-only
            STATUS current
            DESCRIPTION
                "Dc Ammeter hardware version"
            ::= { hwSiteDcAmmeterSampEntry 22 }

        hwSiteDcAmmeterSetTable OBJECT-TYPE
            SYNTAX SEQUENCE OF HwSiteDcAmmeterSetEntry
            MAX-ACCESS not-accessible
             STATUS current
             DESCRIPTION
                "/"
            ::= { hwSiteDcAmmeterEquip 2 }

        hwSiteDcAmmeterSetEntry OBJECT-TYPE
                        SYNTAX HwSiteDcAmmeterSetEntry
            MAX-ACCESS not-accessible
             STATUS current
             DESCRIPTION
                "/"
            INDEX { hwDcAmmeterSetChannelNum }
            ::= { hwSiteDcAmmeterSetTable 1 }

        HwSiteDcAmmeterSetEntry            ::= SEQUENCE {
                hwDcAmmeterSetChannelNum
                    Unsigned32,
                hwDcAmmeterClear
                    INTEGER,
                hwDcAmmeterChannel1DetectionObject

                    INTEGER,
                hwDcAmmeterChannel2DetectionObject

                    INTEGER,
                hwDcAmmeterChannel3DetectionObject

                    INTEGER,
                hwDcAmmeterChannel4DetectionObject

                    INTEGER
            }

        hwDcAmmeterSetChannelNum OBJECT-TYPE
            SYNTAX Unsigned32 (1..4)
            MAX-ACCESS read-write
            STATUS current
            DESCRIPTION
                "Dc Ammeter set channel number, 
                Value range: 1 to 4. 
                Unit: NA.
                and the value is an integer (1).
                If the value is 2147483647(0x7FFFFFFF), it indicates that the value is invalid."
            ::= { hwSiteDcAmmeterSetEntry 1 }

        hwDcAmmeterClear OBJECT-TYPE
            SYNTAX INTEGER
                {
                clear(1)
                }
            MAX-ACCESS read-write
            STATUS current
            DESCRIPTION
                "Dc Ammeter clear communication failure . It is an enumeration type: 
                If the enumeration value is 1, it indicates that the Dc Ammeter clear communication failure alarm;"
            ::= { hwSiteDcAmmeterSetEntry 2 }

        hwDcAmmeterChannel1DetectionObject
 OBJECT-TYPE
            SYNTAX INTEGER
                {
                none(1),
                dcMainEquipment(2),
                dcTCEquipment(3),
                battery(4),
                dcOtherEquipment(5),
                unknown(255)
                }
            MAX-ACCESS read-write
            STATUS current
            DESCRIPTION
                "Detection object of the DC ammeter channel1. It is an enumeration type: 
                If the enumeration value is 1, it indicates that the object is none;
                If the enumeration value is 2, it indicates that the object is DC main equipment;; 
                If the enumeration value is 3, it indicates that the object is DCTC equipment;  
                If the enumeration value is 4, it indicates that the object is battery;  
                If the enumeration value is 5, it indicates that the object is DC other equipment;  
                If the enumeration value is 255, it indicates that the object is unknown."
            ::= { hwSiteDcAmmeterSetEntry 3 }

        hwDcAmmeterChannel2DetectionObject
 OBJECT-TYPE
            SYNTAX INTEGER
                {
                none(1),
                dcMainEquipment(2),
                dcTCEquipment(3),
                battery(4),
                dcOtherEquipment(5),
                unknown(255)
                }
            MAX-ACCESS read-write
            STATUS current
            DESCRIPTION
                "Detection object of the DC ammeter channel2. It is an enumeration type: 
                If the enumeration value is 1, it indicates that the object is none;
                If the enumeration value is 2, it indicates that the object is DC main equipment;; 
                If the enumeration value is 3, it indicates that the object is DCTC equipment;  
                If the enumeration value is 4, it indicates that the object is battery;  
                If the enumeration value is 5, it indicates that the object is DC other equipment;  
                If the enumeration value is 255, it indicates that the object is unknown."
            ::= { hwSiteDcAmmeterSetEntry 4 }

        hwDcAmmeterChannel3DetectionObject
 OBJECT-TYPE
            SYNTAX INTEGER
                {
                none(1),
                dcMainEquipment(2),
                dcTCEquipment(3),
                battery(4),
                dcOtherEquipment(5),
                unknown(255)
                }
            MAX-ACCESS read-write
            STATUS current
            DESCRIPTION
                "Detection object of the DC ammeter channel3. It is an enumeration type: 
                If the enumeration value is 1, it indicates that the object is none;
                If the enumeration value is 2, it indicates that the object is DC main equipment;; 
                If the enumeration value is 3, it indicates that the object is DCTC equipment;  
                If the enumeration value is 4, it indicates that the object is battery;  
                If the enumeration value is 5, it indicates that the object is DC other equipment;  
                If the enumeration value is 255, it indicates that the object is unknown."
            ::= { hwSiteDcAmmeterSetEntry 5 }

        hwDcAmmeterChannel4DetectionObject
 OBJECT-TYPE
            SYNTAX INTEGER
                {
                none(1),
                dcMainEquipment(2),
                dcTCEquipment(3),
                battery(4),
                dcOtherEquipment(5),
                unknown(255)
                }
            MAX-ACCESS read-write
            STATUS current
            DESCRIPTION
                "Detection object of the DC ammeter channel4. It is an enumeration type: 
                If the enumeration value is 1, it indicates that the object is none;
                If the enumeration value is 2, it indicates that the object is DC main equipment;; 
                If the enumeration value is 3, it indicates that the object is DCTC equipment;  
                If the enumeration value is 4, it indicates that the object is battery;  
                If the enumeration value is 5, it indicates that the object is DC other equipment;  
                If the enumeration value is 255, it indicates that the object is unknown."
            ::= { hwSiteDcAmmeterSetEntry 6 }

        hwFuelTank OBJECT IDENTIFIER ::= { hwSiteMonitorMIBObjects 47 }

        hwFuelTankEquip OBJECT IDENTIFIER ::= { hwFuelTank 1 }

        hwFuelTankEquipSampTable OBJECT-TYPE
            SYNTAX SEQUENCE OF HwFuelTankEquipSampEntry
            MAX-ACCESS not-accessible
             STATUS current
             DESCRIPTION
                ""
            ::= { hwFuelTankEquip 1 }

        hwFuelTankEquipSampEntry OBJECT-TYPE
                        SYNTAX HwFuelTankEquipSampEntry
            MAX-ACCESS not-accessible
             STATUS current
             DESCRIPTION
                ""
            INDEX { hwFuelTankEquipIndex }
            ::= { hwFuelTankEquipSampTable 1 }

        HwFuelTankEquipSampEntry            ::= SEQUENCE {
                hwFuelTankEquipIndex
                    Unsigned32,
                hwFuelTankEquipId
                    Unsigned32,
                hwFuelTankEquipName
                    OCTET STRING
            }

        hwFuelTankEquipIndex OBJECT-TYPE
            SYNTAX Unsigned32
            MAX-ACCESS read-only
            STATUS current
            DESCRIPTION
                "Fuel tank device table index."
            ::= { hwFuelTankEquipSampEntry 1 }

        hwFuelTankEquipId OBJECT-TYPE
            SYNTAX Unsigned32
            MAX-ACCESS read-only
            STATUS current
            DESCRIPTION
                "Fuel tank device equipid."
            ::= { hwFuelTankEquipSampEntry 2 }

        hwFuelTankEquipName OBJECT-TYPE
            SYNTAX OCTET STRING (SIZE (0..63))
            MAX-ACCESS read-only
            STATUS current
            DESCRIPTION
                "Fuel tank device equipname."
            ::= { hwFuelTankEquipSampEntry 3 }

        hwPowerController OBJECT IDENTIFIER ::= { hwSiteMonitorMIBObjects 48 }

        hwPowerControllerEquip OBJECT IDENTIFIER ::= { hwPowerController 1 }

        hwPowerControllerEquipSampTable OBJECT-TYPE
            SYNTAX SEQUENCE OF HwPowerControllerEquipSampEntry
            MAX-ACCESS not-accessible
             STATUS current
             DESCRIPTION
                ""
            ::= { hwPowerControllerEquip 1 }

        hwPowerControllerEquipSampEntry OBJECT-TYPE
                        SYNTAX HwPowerControllerEquipSampEntry
            MAX-ACCESS not-accessible
             STATUS current
             DESCRIPTION
                ""
            INDEX { hwPowerControllerEquipIndex }
            ::= { hwPowerControllerEquipSampTable 1 }

        HwPowerControllerEquipSampEntry            ::= SEQUENCE {
                hwPowerControllerEquipIndex
                    Unsigned32,
                hwPowerControllerEquipId
                    Unsigned32,
                hwPowerControllerEquipName
                    OCTET STRING,
                hwPowerControllerEquipAddress
                    Unsigned32,
                hwPowerControllerConnectedPort
                    OCTET STRING,
                hwPowerControllerMainEquipTemp 
                    Integer32,
                hwPowerControllerMainEquipHumidity 
                    Unsigned32,
                hwPowerControllerReturnAirTemp 
                    Integer32,
                hwPowerControllerAmbientTemp 
                    Integer32,
                hwPowerControllerDCPowerBrand 
                    OCTET STRING,
                hwPowerControllerACVoltage 
                    Unsigned32,
                hwPowerControllerQtyOfRect 
                    Unsigned32,
                hwPowerControllerRectifierCurrent1
                    Unsigned32,
                hwPowerControllerRectifierCurrent2
                    Unsigned32,
                hwPowerControllerRectifierCurrent3
                    Unsigned32,
                hwPowerControllerRectifierCurrent4
                    Unsigned32,
                hwPowerControllerRectifierCurrent5
                    Unsigned32,
                hwPowerControllerRectifierCurrent6
                    Unsigned32,
                hwPowerControllerRectifierCurrent7
                    Unsigned32,
                hwPowerControllerRectifierCurrent8
                    Unsigned32,
                hwPowerControllerRectifierCurrent9
                    Unsigned32,
                hwPowerControllerRectifierCurrent10
                    Unsigned32,
                hwPowerControllerRectifierCurrent11
                    Unsigned32,
                hwPowerControllerRectifierCurrent12
                    Unsigned32,
                hwPowerControllerRectifierState1 
                    INTEGER,
                hwPowerControllerRectifierState2
                    INTEGER,
                hwPowerControllerRectifierState3
                    INTEGER,
                hwPowerControllerRectifierState4
                    INTEGER,
                hwPowerControllerRectifierState5
                    INTEGER,
                hwPowerControllerRectifierState6
                    INTEGER,
                hwPowerControllerRectifierState7
                    INTEGER,
                hwPowerControllerRectifierState8
                    INTEGER,
                hwPowerControllerRectifierState9
                    INTEGER,
                hwPowerControllerRectifierState10
                    INTEGER,
                hwPowerControllerRectifierState11
                    INTEGER,
                hwPowerControllerRectifierState12
                    INTEGER,
                hwPowerControllerRectifierBrand 
                    OCTET STRING,
                hwPowerControllerDCVoltage 
                    Unsigned32,
                hwPowerControllerTotalLoadCurrent 
                    Integer32,
                hwPowerControllerDCEnergyConsump 
                    Unsigned32,
                hwPowerControllerQtyOfBattStr 
                    Unsigned32,
                hwPowerControllerBatteryCurrent 
                    Integer32,
                hwPowerControllerBatteryTemperature 
                    Integer32,
                hwPowerControllerBatterySOC 
                    Unsigned32,
                hwPowerControllerBatteryRatedCapacity 
                    Unsigned32,
                hwPowerControllerBatteryManagementState 
                    INTEGER,
                hwPowerControllerSoftwareVersion 
                    OCTET STRING,
                hwPowerControllerACConsumption 
                    Unsigned32,
                hwPowerControllerDCOutputPower 
                    Unsigned32
            }

        hwPowerControllerEquipIndex OBJECT-TYPE
            SYNTAX Unsigned32 (4096..20479)
            MAX-ACCESS read-only
            STATUS current
            DESCRIPTION
                "Power Controller table index,which value range:4096 to 20479. Lines of the device list are restricted by the quantity of Power Controller"
            ::= { hwPowerControllerEquipSampEntry 1 }

        hwPowerControllerEquipId OBJECT-TYPE
            SYNTAX Unsigned32
            MAX-ACCESS read-only
            STATUS current
            DESCRIPTION
                "Power Controller device ID. "
            ::= { hwPowerControllerEquipSampEntry 2 }

        hwPowerControllerEquipName OBJECT-TYPE
            SYNTAX OCTET STRING (SIZE (0..63))
            MAX-ACCESS read-only
            STATUS current
            DESCRIPTION
                "Power Controller name, of the character string type, is used to specify Power Controller. Users can configure it.
                Otherwise, the configured character can not be any other languages except English.
                "
            ::= { hwPowerControllerEquipSampEntry 3 }

        hwPowerControllerEquipAddress OBJECT-TYPE
            SYNTAX Unsigned32 (0..65535)
            MAX-ACCESS read-only
            STATUS current
            DESCRIPTION
                "Power Controller communica address."
            ::= { hwPowerControllerEquipSampEntry 4 }

        hwPowerControllerConnectedPort OBJECT-TYPE
            SYNTAX OCTET STRING (SIZE (0..60))
            MAX-ACCESS read-only
            STATUS current
            DESCRIPTION
                "Power Controller communica Port."
            ::= { hwPowerControllerEquipSampEntry 5 }

        hwPowerControllerMainEquipTemp  OBJECT-TYPE
            SYNTAX Integer32 ( -1000..1000)
            MAX-ACCESS read-only
            STATUS current
            DESCRIPTION
                "Power controller main equip temperature. Value range: -100 to 100, unit: degC, and the value is accurate to one decimal space (.1). If the value is 2147483647(0x7FFFFFFF), it indicates that the value is invalid."
            ::= { hwPowerControllerEquipSampEntry 6 }

        hwPowerControllerMainEquipHumidity  OBJECT-TYPE
            SYNTAX Unsigned32 ( 0..1000)
            MAX-ACCESS read-only
            STATUS current
            DESCRIPTION
                "Power controller main equip humility. It is an environment parameter collected in real time. Value range: 0 to 100, unit: %, and the value is an integer (1). If the value is 2147483647(0x7FFFFFFF), it indicates that the humidity sensor is not configured."
            ::= { hwPowerControllerEquipSampEntry 7 }

        hwPowerControllerReturnAirTemp  OBJECT-TYPE
            SYNTAX Integer32 ( -1000..1000)
            MAX-ACCESS read-only
            STATUS current
            DESCRIPTION
                "Power controller return air temperature. Value range: -100 to 100, unit: degC, and the value is accurate to one decimal space (.1). If the value is 2147483647(0x7FFFFFFF), it indicates that the value is invalid."
            ::= { hwPowerControllerEquipSampEntry 8 }

        hwPowerControllerAmbientTemp  OBJECT-TYPE
            SYNTAX Integer32 ( -1000..1000)
            MAX-ACCESS read-only
            STATUS current
            DESCRIPTION
                "Power controller ambient temperature. Value range: -100 to 100, unit: degC, and the value is accurate to one decimal space (.1). If the value is 2147483647(0x7FFFFFFF), it indicates that the value is invalid."
            ::= { hwPowerControllerEquipSampEntry 9 }

        hwPowerControllerDCPowerBrand  OBJECT-TYPE
            SYNTAX OCTET STRING (SIZE (0..60))
            MAX-ACCESS read-only
            STATUS current
            DESCRIPTION
                "Power controller DC power brand."
            ::= { hwPowerControllerEquipSampEntry 10 }

        hwPowerControllerACVoltage  OBJECT-TYPE
            SYNTAX Unsigned32 ( 0..4000)
            MAX-ACCESS read-only
            STATUS current
            DESCRIPTION
                "The AC volt; 
                Value range: 0 to 400, 
                and the value is accurate to one decimal place (.1).  
                If the value is 2147483647(0x7FFFFFFF), 
                it indicates that the value is invalid. 
                unit: V."
            ::= { hwPowerControllerEquipSampEntry 11 }

        hwPowerControllerQtyOfRect  OBJECT-TYPE
            SYNTAX Unsigned32 (0..50)
            MAX-ACCESS read-only
            STATUS current
            DESCRIPTION
                "Number of the rectifiers."
            ::= { hwPowerControllerEquipSampEntry 12 }

        hwPowerControllerRectifierCurrent1 OBJECT-TYPE
            SYNTAX Unsigned32 (0..3000)
            MAX-ACCESS read-only
            STATUS current
            DESCRIPTION
                "Output current of the rectifier module1. It is a real-time analog parameter. Value range: 0 to 300, unit: A, and the value is accurate to one decimal place (.1).  If the value is 2147483647(0x7FFFFFFF), it indicates that the value is invalid."
            ::= { hwPowerControllerEquipSampEntry 13 }

        hwPowerControllerRectifierCurrent2 OBJECT-TYPE
            SYNTAX Unsigned32 (0..3000)
            MAX-ACCESS read-only
            STATUS current
            DESCRIPTION
                "Output current of the rectifier module2. It is a real-time analog parameter. Value range: 0 to 300, unit: A, and the value is accurate to one decimal place (.1).  If the value is 2147483647(0x7FFFFFFF), it indicates that the value is invalid."
            ::= { hwPowerControllerEquipSampEntry 14 }

        hwPowerControllerRectifierCurrent3 OBJECT-TYPE
            SYNTAX Unsigned32 (0..3000)
            MAX-ACCESS read-only
            STATUS current
            DESCRIPTION
                "Output current of the rectifier module3. It is a real-time analog parameter. Value range: 0 to 300, unit: A, and the value is accurate to one decimal place (.1).  If the value is 2147483647(0x7FFFFFFF), it indicates that the value is invalid."
            ::= { hwPowerControllerEquipSampEntry 15 }

        hwPowerControllerRectifierCurrent4 OBJECT-TYPE
            SYNTAX Unsigned32 (0..3000)
            MAX-ACCESS read-only
            STATUS current
            DESCRIPTION
                "Output current of the rectifier module4. It is a real-time analog parameter. Value range: 0 to 300, unit: A, and the value is accurate to one decimal place (.1).  If the value is 2147483647(0x7FFFFFFF), it indicates that the value is invalid."
            ::= { hwPowerControllerEquipSampEntry 16 }

        hwPowerControllerRectifierCurrent5 OBJECT-TYPE
            SYNTAX Unsigned32 (0..3000)
            MAX-ACCESS read-only
            STATUS current
            DESCRIPTION
                "Output current of the rectifier module5. It is a real-time analog parameter. Value range: 0 to 300, unit: A, and the value is accurate to one decimal place (.1).  If the value is 2147483647(0x7FFFFFFF), it indicates that the value is invalid."
            ::= { hwPowerControllerEquipSampEntry 17 }

        hwPowerControllerRectifierCurrent6 OBJECT-TYPE
            SYNTAX Unsigned32 (0..3000)
            MAX-ACCESS read-only
            STATUS current
            DESCRIPTION
                "Output current of the rectifier module6. It is a real-time analog parameter. Value range: 0 to 300, unit: A, and the value is accurate to one decimal place (.1).  If the value is 2147483647(0x7FFFFFFF), it indicates that the value is invalid."
            ::= { hwPowerControllerEquipSampEntry 18 }

        hwPowerControllerRectifierCurrent7 OBJECT-TYPE
            SYNTAX Unsigned32 (0..3000)
            MAX-ACCESS read-only
            STATUS current
            DESCRIPTION
                "Output current of the rectifier module7. It is a real-time analog parameter. Value range: 0 to 300, unit: A, and the value is accurate to one decimal place (.1).  If the value is 2147483647(0x7FFFFFFF), it indicates that the value is invalid."
            ::= { hwPowerControllerEquipSampEntry 19 }

        hwPowerControllerRectifierCurrent8 OBJECT-TYPE
            SYNTAX Unsigned32 (0..3000)
            MAX-ACCESS read-only
            STATUS current
            DESCRIPTION
                "Output current of the rectifier module8. It is a real-time analog parameter. Value range: 0 to 300, unit: A, and the value is accurate to one decimal place (.1).  If the value is 2147483647(0x7FFFFFFF), it indicates that the value is invalid."
            ::= { hwPowerControllerEquipSampEntry 20 }

        hwPowerControllerRectifierCurrent9 OBJECT-TYPE
            SYNTAX Unsigned32 (0..3000)
            MAX-ACCESS read-only
            STATUS current
            DESCRIPTION
                "Output current of the rectifier module9. It is a real-time analog parameter. Value range: 0 to 300, unit: A, and the value is accurate to one decimal place (.1).  If the value is 2147483647(0x7FFFFFFF), it indicates that the value is invalid."
            ::= { hwPowerControllerEquipSampEntry 21 }

        hwPowerControllerRectifierCurrent10 OBJECT-TYPE
            SYNTAX Unsigned32 (0..3000)
            MAX-ACCESS read-only
            STATUS current
            DESCRIPTION
                "Output current of the rectifier module10. It is a real-time analog parameter. Value range: 0 to 300, unit: A, and the value is accurate to one decimal place (.1).  If the value is 2147483647(0x7FFFFFFF), it indicates that the value is invalid."
            ::= { hwPowerControllerEquipSampEntry 22 }

        hwPowerControllerRectifierCurrent11 OBJECT-TYPE
            SYNTAX Unsigned32 (0..3000)
            MAX-ACCESS read-only
            STATUS current
            DESCRIPTION
                "Output current of the rectifier module11. It is a real-time analog parameter. Value range: 0 to 300, unit: A, and the value is accurate to one decimal place (.1).  If the value is 2147483647(0x7FFFFFFF), it indicates that the value is invalid."
            ::= { hwPowerControllerEquipSampEntry 23 }

        hwPowerControllerRectifierCurrent12 OBJECT-TYPE
            SYNTAX Unsigned32 (0..3000)
            MAX-ACCESS read-only
            STATUS current
            DESCRIPTION
                "Output current of the rectifier module12. It is a real-time analog parameter. Value range: 0 to 300, unit: A, and the value is accurate to one decimal place (.1).  If the value is 2147483647(0x7FFFFFFF), it indicates that the value is invalid."
            ::= { hwPowerControllerEquipSampEntry 24 }

        hwPowerControllerRectifierState1  OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module1. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 25 }

        hwPowerControllerRectifierState2 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module2. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 26 }

        hwPowerControllerRectifierState3 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module3. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 27 }

        hwPowerControllerRectifierState4 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module4. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 28 }

        hwPowerControllerRectifierState5 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module5. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 29 }

        hwPowerControllerRectifierState6 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module6. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 30 }

        hwPowerControllerRectifierState7 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module7. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 31 }

        hwPowerControllerRectifierState8 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module8. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 32 }

        hwPowerControllerRectifierState9 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module9. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 33 }

        hwPowerControllerRectifierState10 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module10. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 34 }

        hwPowerControllerRectifierState11 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module11. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 35 }

        hwPowerControllerRectifierState12 OBJECT-TYPE
            SYNTAX INTEGER
                {
                normal(1),
                fault(2),
                protect(3),
                commFail(4),
                powerOff(5),
                invalid(6),
                noConfig(7),
                powerFailure(8),
                dormant(9),
                unknown(255)
                }
            MAX-ACCESS read-only
            STATUS current
            DESCRIPTION
                "State of the rectifier module12. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                  If the enumeration value is 8, this rectifier is power failure;
                  If the enumeration value is 9, this rectifier is dormant; 
                  If the enumeration value is 255, rectifier operation status unknown."
            ::= { hwPowerControllerEquipSampEntry 36 }

        hwPowerControllerRectifierBrand  OBJECT-TYPE
            SYNTAX OCTET STRING (SIZE (0..60))
            MAX-ACCESS read-only
            STATUS current
            DESCRIPTION
                "Power controller Rectifier brand."
            ::= { hwPowerControllerEquipSampEntry 37 }

        hwPowerControllerDCVoltage  OBJECT-TYPE
            SYNTAX Unsigned32 (0..1000)
            MAX-ACCESS read-only
            STATUS current
            DESCRIPTION
                "The DC volt; 
                Value range: 0 to 100, 
                and the value is accurate to one decimal place (.1).   
                If the value is 2147483647(0x7FFFFFFF), 
                it indicates that the value is invalid. 
                unit: V."
            ::= { hwPowerControllerEquipSampEntry 38 }

        hwPowerControllerTotalLoadCurrent  OBJECT-TYPE
            SYNTAX Integer32 ( -300000..300000)
            MAX-ACCESS read-only
            STATUS current
            DESCRIPTION
                "Load current: -30000 to 30000, 
                
                unit: A, 
                
                and the value is one decimal space (.1). If the value is 2147483647(0x7FFFFFFF), it indicates that the value is invalid."
            ::= { hwPowerControllerEquipSampEntry 39 }

        hwPowerControllerDCEnergyConsump  OBJECT-TYPE
            SYNTAX Unsigned32 ( 0..1000000000)
            MAX-ACCESS read-only
            STATUS current
            DESCRIPTION
                "Power controller dc energy consumption , 
                Value range:0 to 10000000.00.
                Unit: kWh.
                and the value is accurate to two decimal space (.01). 
                If the value is 2147483647(0x7FFFFFFF), it indicates that the value is invalid."
            ::= { hwPowerControllerEquipSampEntry 40 }

        hwPowerControllerQtyOfBattStr  OBJECT-TYPE
            SYNTAX Unsigned32 (0..50)
            MAX-ACCESS read-only
            STATUS current
            DESCRIPTION
                "Number of the Battary String."
            ::= { hwPowerControllerEquipSampEntry 41 }

        hwPowerControllerBatteryCurrent  OBJECT-TYPE
            SYNTAX Integer32 ( -10000..10000)
            MAX-ACCESS read-only
            STATUS current
            DESCRIPTION
                "The battery current; Value range: -1000 to 1000, 
                unit: A. 
                and the value is accurate to one decimal place (.1).  
                If the value is 2147483647(0x7FFFFFFF), it indicates that the value is invalid."
            ::= { hwPowerControllerEquipSampEntry 42 }

        hwPowerControllerBatteryTemperature  OBJECT-TYPE
            SYNTAX Integer32 ( -400..1000)
            MAX-ACCESS read-only
            STATUS current
            DESCRIPTION
                "Battery temperature. It is a battery parameter collected in real time. 
                Value range: -40 to 100, 
                unit: centigrade (degC), 
                and the value is accurate to one decimal place (.1).  
                If the value is 2147483647(0x7FFFFFFF), it indicates that battery temperature is not configured."
            ::= { hwPowerControllerEquipSampEntry 43 }

        hwPowerControllerBatterySOC  OBJECT-TYPE
            SYNTAX Unsigned32 (0..100)
            MAX-ACCESS read-only
            STATUS current
            DESCRIPTION
                "Total Remaining Capacity Percent. Value range: 0 to 100, unit: %, and the value is an integer. If the value is 2147483647(0x7FFFFFFF), it indicates that the value is invalid."
            ::= { hwPowerControllerEquipSampEntry 44 }

        hwPowerControllerBatteryRatedCapacity  OBJECT-TYPE
            SYNTAX Unsigned32 (0..65535)
            MAX-ACCESS read-only
            STATUS current
            DESCRIPTION
                " batteries rated capacity. It is an analog parameter collected by the battery string in real time.Value range: 0 to 65535, unit: Ah, the value is an integer (1). If the value is 2147483647(0x7FFFFFFF), it indicates that the value is invalid."
            ::= { hwPowerControllerEquipSampEntry 45 }

        hwPowerControllerBatteryManagementState  OBJECT-TYPE
            SYNTAX INTEGER
                {
                fcharging(1),
                bcharging(2),
                enforce(3),
                discharging(4),
                dormant(5),
                unknown(255)
                }
            MAX-ACCESS read-only
            STATUS current
            DESCRIPTION
                "State of the battery management.It is an enumeration type:
                If the enumeration value is 1, it indicates that battery is on float charging,
                If the enumeration value is 2,it indicates that battery is on equal charging,
                If the enumeration value is 3, it indicates the battery is enforce on equal charging,
                If the enumeration value is 4, , it indicates that battery is on discharge,
                If the enumeration value is 5, it indicates  that battery dormant,
                  If the enumeration value is 255, that battery operation status unknown."
            ::= { hwPowerControllerEquipSampEntry 46 }

        hwPowerControllerSoftwareVersion  OBJECT-TYPE
            SYNTAX OCTET STRING (SIZE (0..60))
            MAX-ACCESS read-only
            STATUS current
            DESCRIPTION
                "Monitor software version. It is of the character string type."
            ::= { hwPowerControllerEquipSampEntry 47 }

        hwPowerControllerACConsumption  OBJECT-TYPE
            SYNTAX Unsigned32 ( 0..1000000000)
            MAX-ACCESS read-only
            STATUS current
            DESCRIPTION
                "Power controller ac consumption, 
                Value range:0 to 10000000.00.
                Unit: kWh.
                and the value is accurate to two decimal space (.01). 
                If the value is 2147483647(0x7FFFFFFF), it indicates that the value is invalid."
            ::= { hwPowerControllerEquipSampEntry 48 }

        hwPowerControllerDCOutputPower  OBJECT-TYPE
            SYNTAX Unsigned32 ( 0..300000)
            MAX-ACCESS read-only
            STATUS current
            DESCRIPTION
                "Power controller dc output power, 
                Value range:0 to 3000.00.
                Unit: kW.
                and the value is accurate to two decimal space (.01). 
                If the value is 2147483647(0x7FFFFFFF), it indicates that the value is invalid."
            ::= { hwPowerControllerEquipSampEntry 49 }

        hwPowerControllerSetTable OBJECT-TYPE
            SYNTAX SEQUENCE OF HwPowerControllerSetEntry
            MAX-ACCESS not-accessible
             STATUS current
             DESCRIPTION
                ""
            ::= { hwPowerControllerEquip 2 }

        hwPowerControllerSetEntry OBJECT-TYPE
                        SYNTAX HwPowerControllerSetEntry
            MAX-ACCESS not-accessible
             STATUS current
             DESCRIPTION
                ""
            INDEX { hwPowerControllerDelEquip }
            ::= { hwPowerControllerSetTable 1 }

        HwPowerControllerSetEntry            ::= SEQUENCE {
                hwPowerControllerDelEquip
                    INTEGER
            }

        hwPowerControllerDelEquip OBJECT-TYPE
            SYNTAX INTEGER
                {
                yes(1)
                }
            MAX-ACCESS read-write
            STATUS current
            DESCRIPTION
                "Delete communication failure equipments of the power controller. It is an enumeration type:
                If the enumeration value is 1, it indicates that deletes communication failure equipments;"
            ::= { hwPowerControllerSetEntry 1 }

        hwSiteMimo OBJECT IDENTIFIER ::= { hwSiteMonitorMIBObjects 49 }

        hwMimoGroup OBJECT IDENTIFIER ::= { hwSiteMimo 1 }

        hwMimoGroupTable OBJECT-TYPE
            SYNTAX SEQUENCE OF HwMimoGroupEntry
            MAX-ACCESS not-accessible
             STATUS current
             DESCRIPTION
                ""
            ::= { hwMimoGroup 1 }

        hwMimoGroupEntry OBJECT-TYPE
                        SYNTAX HwMimoGroupEntry
            MAX-ACCESS not-accessible
             STATUS current
             DESCRIPTION
                ""
            INDEX { hwMimoGroupEquipIndex }
            ::= { hwMimoGroupTable 1 }

        HwMimoGroupEntry            ::= SEQUENCE {
                hwMimoGroupEquipIndex
                    Unsigned32,
                hwMimoGroupEquipId
                    Unsigned32,
                hwMimoGroupEquipName
                    OCTET STRING,
                hwMimoGroupSet12DcOutputVolt
                    Unsigned32,
                hwMimoGroupSet24AcOutputVolt
                    Unsigned32,
                hwMimoGroupClearMimoLostAlarm
                    INTEGER,
                hwMimoGroupClearCommFailEquip
                    INTEGER
            }

        hwMimoGroupEquipIndex OBJECT-TYPE
            SYNTAX Unsigned32
            MAX-ACCESS read-only
            STATUS current
            DESCRIPTION
                "Mimo group table index. Lines of the device list are restricted by the quantity of Mimo group."
            ::= { hwMimoGroupEntry 1 }

        hwMimoGroupEquipId OBJECT-TYPE
            SYNTAX Unsigned32
            MAX-ACCESS read-only
            STATUS current
            DESCRIPTION
                "Mimo group device ID."
            ::= { hwMimoGroupEntry 2 }

        hwMimoGroupEquipName OBJECT-TYPE
            SYNTAX OCTET STRING (SIZE (0..63))
            MAX-ACCESS read-only
            STATUS current
            DESCRIPTION
                "Mimo group name, of the character string type, is used to specify mimo group.
                "
            ::= { hwMimoGroupEntry 3 }

        hwMimoGroupSet12DcOutputVolt OBJECT-TYPE
            SYNTAX Unsigned32 (120..132)
            MAX-ACCESS read-write
            STATUS current
            DESCRIPTION
                "The 12 DC default output volt; 
                Value range: 12 to 13.2, 
                and the value is accurate to one decimal place (.1).   
                If the value is 2147483647(0x7FFFFFFF), 
                it indicates that the value is invalid. 
                unit: V."
            ::= { hwMimoGroupEntry 4 }

        hwMimoGroupSet24AcOutputVolt OBJECT-TYPE
            SYNTAX Unsigned32 (240..263)
            MAX-ACCESS read-write
            STATUS current
            DESCRIPTION
                "The 24 AC default output volt; 
                Value range: 24 to 26.3, 
                and the value is accurate to one decimal place (.1).   
                If the value is 2147483647(0x7FFFFFFF), 
                it indicates that the value is invalid. 
                unit: V."
            ::= { hwMimoGroupEntry 6 }

        hwMimoGroupClearMimoLostAlarm OBJECT-TYPE
            SYNTAX INTEGER
                {
                yes(1)
                }
            MAX-ACCESS read-write
            STATUS current
            DESCRIPTION
                "Clear lost alarm of the mimo. It is an enumeration type:
                If the enumeration value is 1, it indicates that Clear lost alarm."
            ::= { hwMimoGroupEntry 7 }

        hwMimoGroupClearCommFailEquip OBJECT-TYPE
            SYNTAX INTEGER
                {
                clear(1)
                }
            MAX-ACCESS read-write
            STATUS current
            DESCRIPTION
                "Mimo group clear communication failure equip. It is an enumeration type: 
                If the enumeration value is 1, it indicates that the mimo group clear communication failure equip."
            ::= { hwMimoGroupEntry 8 }

        hwMimoEquip OBJECT IDENTIFIER ::= { hwSiteMimo 2 }

        hwMimoSampTable OBJECT-TYPE
            SYNTAX SEQUENCE OF HwMimoSampEntry
            MAX-ACCESS not-accessible
             STATUS current
             DESCRIPTION
                ""
            ::= { hwMimoEquip 1 }

        hwMimoSampEntry OBJECT-TYPE
                        SYNTAX HwMimoSampEntry
            MAX-ACCESS not-accessible
             STATUS current
             DESCRIPTION
                ""
            INDEX { hwMimoEquipIndex }
            ::= { hwMimoSampTable 1 }

        HwMimoSampEntry            ::= SEQUENCE {
                hwMimoEquipIndex
                    Unsigned32,
                hwMimoEquipId
                    Unsigned32,
                hwMimoEquipName
                    OCTET STRING,
                hwMimoEquipFatherEquipName
                    OCTET STRING,
                hwMimo12DcOutputVolt
                    Unsigned32,
                hwMimo12DcOutputCur
                    Unsigned32,
                hwMimo24DcOutputVolt
                    Unsigned32,
                hwMimo24DcOutputCur
                    Unsigned32,
                hwMimo24AcOutputVolt
                    Unsigned32,
                hwMimo24AcOutputCur
                    Unsigned32,
                hwMimoSoftwareVersion
                    OCTET STRING,
                hwMimoHardwareVersion
                    OCTET STRING
            }

        hwMimoEquipIndex OBJECT-TYPE
            SYNTAX Unsigned32
            MAX-ACCESS read-only
            STATUS current
            DESCRIPTION
                "Mimo equip table index. Lines of the device list are restricted by the quantity of Mimo."
            ::= { hwMimoSampEntry 1 }

        hwMimoEquipId OBJECT-TYPE
            SYNTAX Unsigned32
            MAX-ACCESS read-only
            STATUS current
            DESCRIPTION
                "Mimo equip device ID."
            ::= { hwMimoSampEntry 2 }

        hwMimoEquipName OBJECT-TYPE
            SYNTAX OCTET STRING (SIZE (0..63))
            MAX-ACCESS read-only
            STATUS current
            DESCRIPTION
                "Mimo equip name, of the character string type, is used to specify mimo equip."
            ::= { hwMimoSampEntry 3 }

        hwMimoEquipFatherEquipName OBJECT-TYPE
            SYNTAX OCTET STRING (SIZE (0..63))
            MAX-ACCESS read-only
            STATUS current
            DESCRIPTION
                "Name of the parent device of the mimo equip."
            ::= { hwMimoSampEntry 4 }

        hwMimo12DcOutputVolt OBJECT-TYPE
            SYNTAX Unsigned32 (0..1000)
            MAX-ACCESS read-only
            STATUS current
            DESCRIPTION
                "The 12 DC default output voltage; 
                Value range: 0 to 100, 
                and the value is accurate to one decimal place (.1).   
                If the value is 2147483647(0x7FFFFFFF), 
                it indicates that the value is invalid. 
                unit: V."
            ::= { hwMimoSampEntry 5 }

        hwMimo12DcOutputCur OBJECT-TYPE
            SYNTAX Unsigned32 (0..1000)
            MAX-ACCESS read-only
            STATUS current
            DESCRIPTION
                "The 12 DC default output current; 
                Value range: 0 to 100, 
                and the value is accurate to one decimal place (.1).   
                If the value is 2147483647(0x7FFFFFFF), 
                it indicates that the value is invalid. 
                unit: A."
            ::= { hwMimoSampEntry 6 }

        hwMimo24DcOutputVolt OBJECT-TYPE
            SYNTAX Unsigned32 (0..1000)
            MAX-ACCESS read-only
            STATUS current
            DESCRIPTION
                "The 24 DC default output voltage; 
                Value range: 0 to 100, 
                and the value is accurate to one decimal place (.1).   
                If the value is 2147483647(0x7FFFFFFF), 
                it indicates that the value is invalid. 
                unit: V."
            ::= { hwMimoSampEntry 7 }

        hwMimo24DcOutputCur OBJECT-TYPE
            SYNTAX Unsigned32 (0..1000)
            MAX-ACCESS read-only
            STATUS current
            DESCRIPTION
                "The 24 DC default output current; 
                Value range: 0 to 100, 
                and the value is accurate to one decimal place (.1).   
                If the value is 2147483647(0x7FFFFFFF), 
                it indicates that the value is invalid. 
                unit: A."
            ::= { hwMimoSampEntry 8 }

        hwMimo24AcOutputVolt OBJECT-TYPE
            SYNTAX Unsigned32 (0..1000)
            MAX-ACCESS read-only
            STATUS current
            DESCRIPTION
                "The 24 AC default output voltage; 
                Value range: 0 to 100, 
                and the value is accurate to one decimal place (.1).   
                If the value is 2147483647(0x7FFFFFFF), 
                it indicates that the value is invalid. 
                unit: V."
            ::= { hwMimoSampEntry 9 }

        hwMimo24AcOutputCur OBJECT-TYPE
            SYNTAX Unsigned32 (0..1000)
            MAX-ACCESS read-only
            STATUS current
            DESCRIPTION
                "The 24 AC default output current; 
                Value range: 0 to 100, 
                and the value is accurate to one decimal place (.1).   
                If the value is 2147483647(0x7FFFFFFF), 
                it indicates that the value is invalid. 
                unit: A."
            ::= { hwMimoSampEntry 10 }

        hwMimoSoftwareVersion OBJECT-TYPE
            SYNTAX OCTET STRING (SIZE (0..63))
            MAX-ACCESS read-only
            STATUS current
            DESCRIPTION
                "Mimo equip software verison."
            ::= { hwMimoSampEntry 11 }

        hwMimoHardwareVersion OBJECT-TYPE
            SYNTAX OCTET STRING (SIZE (0..63))
            MAX-ACCESS read-only
            STATUS current
            DESCRIPTION
                "Mimo equip hardware version"
            ::= { hwMimoSampEntry 12 }

        hwMimoSetTable OBJECT-TYPE
            SYNTAX SEQUENCE OF HwMimoSetEntry
            MAX-ACCESS not-accessible
             STATUS current
             DESCRIPTION
                ""
            ::= { hwMimoEquip 2 }

        hwMimoSetEntry OBJECT-TYPE
                        SYNTAX HwMimoSetEntry
            MAX-ACCESS not-accessible
             STATUS current
             DESCRIPTION
                ""
            INDEX { hwMimoSet12DcTurnOffOn }
            ::= { hwMimoSetTable 1 }

        HwMimoSetEntry            ::= SEQUENCE {
                hwMimoSet12DcTurnOffOn
                    INTEGER,
                hwMimoSet24DcTurnOffOn
                    INTEGER,
                hwMimoSet24AcTurnOffOn
                    INTEGER
            }

        hwMimoSet12DcTurnOffOn OBJECT-TYPE
            SYNTAX INTEGER
                {
                on(1),
                off(2),
                unknow(255)
                }
            MAX-ACCESS read-write
            STATUS current
            DESCRIPTION
                "Power-on or power-off of the 12 DC output. It is an enumeration value:
                If the enumeration value is 1, it indicates power-on of the 12 DC output;
                If the enumeration value is 2, it indicates power-off of the 12 DC output.
                If the enumeration value is 255,that 12 DC output status unknown.."
            ::= { hwMimoSetEntry 1 }

        hwMimoSet24DcTurnOffOn OBJECT-TYPE
            SYNTAX INTEGER
                {
                on(1),
                off(2),
                unknow(255)
                }
            MAX-ACCESS read-write
            STATUS current
            DESCRIPTION
                "Power-on or power-off of the 24 DC output. It is an enumeration value:
                If the enumeration value is 1, it indicates power-on of the 24 DC output;
                If the enumeration value is 2, it indicates power-off of the 24 DC output.
                If the enumeration value is 255,that 24 DC output status unknown.."
            ::= { hwMimoSetEntry 2 }

        hwMimoSet24AcTurnOffOn OBJECT-TYPE
            SYNTAX INTEGER
                {
                on(1),
                off(2),
                unknow(255)
                }
            MAX-ACCESS read-write
            STATUS current
            DESCRIPTION
                "Power-on or power-off of the 24 AC output. It is an enumeration value:
                If the enumeration value is 1, it indicates power-on of the 24 AC output;
                If the enumeration value is 2, it indicates power-off of the 24 AC output.
                If the enumeration value is 255,that 24 AC output status unknown.."
            ::= { hwMimoSetEntry 3 }

        hwSiteIcbd OBJECT IDENTIFIER ::= { hwSiteMonitorMIBObjects 50 }

        hwIcbdGeneral OBJECT IDENTIFIER ::= { hwSiteIcbd 1 }

        hwIcbdGeneralTable OBJECT-TYPE
            SYNTAX SEQUENCE OF HwIcbdGeneralEntry
            MAX-ACCESS not-accessible
             STATUS current
             DESCRIPTION
                ""
            ::= { hwIcbdGeneral 1 }

        hwIcbdGeneralEntry OBJECT-TYPE
                        SYNTAX HwIcbdGeneralEntry
            MAX-ACCESS not-accessible
             STATUS current
             DESCRIPTION
                ""
            INDEX { hwIcbdGeneralEquipIndex }
            ::= { hwIcbdGeneralTable 1 }

        HwIcbdGeneralEntry            ::= SEQUENCE {
                hwIcbdGeneralEquipIndex
                    Unsigned32,
                hwIcbdGeneralEquipId
                    Unsigned32,
                hwIcbdGeneralEquipName
                    OCTET STRING,
                hwIcbdGeneralFahterEquipName
                    OCTET STRING,
                hwIcbdGeneralBranchUsage
                    INTEGER,
                hwIcbdGeneralRatedCapacity
                    Unsigned32,
                hwIcbdGeneralCurrent
                    Integer32,
                hwIcbdGeneralTotalInputEnergy
                    Unsigned32,
                hwIcbdGeneralOCThreshold
                    Unsigned32,
                hwIcbdGeneralEnbManualCtrl
                    INTEGER,
                hwIcbdGeneralTotalOutputEnergy
                    Unsigned32,
                hwIcbdGeneralDCVolt
                    Unsigned32,
                hwIcbdGeneralTemperature
                    Integer32
            }

        hwIcbdGeneralEquipIndex OBJECT-TYPE
            SYNTAX Unsigned32
            MAX-ACCESS read-only
            STATUS current
            DESCRIPTION
                "ICBD general table index. Lines of the device list are restricted by the quantity of Mimo group."
            ::= { hwIcbdGeneralEntry 1 }

        hwIcbdGeneralEquipId OBJECT-TYPE
            SYNTAX Unsigned32
            MAX-ACCESS read-only
            STATUS current
            DESCRIPTION
                "ICBD general device ID."
            ::= { hwIcbdGeneralEntry 2 }

        hwIcbdGeneralEquipName OBJECT-TYPE
            SYNTAX OCTET STRING (SIZE (0..63))
            MAX-ACCESS read-only
            STATUS current
            DESCRIPTION
                "ICBD general name, of the character string type, is used to specify ICBD general equip.
                "
            ::= { hwIcbdGeneralEntry 3 }

        hwIcbdGeneralFahterEquipName OBJECT-TYPE
            SYNTAX OCTET STRING (SIZE (0..63))
            MAX-ACCESS read-only
            STATUS current
            DESCRIPTION
                "ICBD general name, of the character string type, is used to specify ICBD general father equip."
            ::= { hwIcbdGeneralEntry 4 }

        hwIcbdGeneralBranchUsage OBJECT-TYPE
            SYNTAX INTEGER
                {
                leadAcidBattery(1),
                lithiumBattery(2),
                solarEnergy(3),
                dcGenset(4),
                powerCascadingPort(5),
                others(6),
                temperatureControl(7),
                windEnergy(8),
                otherGreenEnergy(9),
                tripartitePwParalConPrt(10)
                }
            MAX-ACCESS read-only
            STATUS current
            DESCRIPTION
                "State of the ICBD general branch usage.It is an enumeration type:
                If the enumeration value is 1, it indicates that branch usage is blvd Load,
                If the enumeration value is 2,it indicates that branch usage is customized load,
                If the enumeration value is 3, it indicates that branch usage is lead acid battery,
                If the enumeration value is 4, , it indicates that branch usage is lithium battery,
                If the enumeration value is 5, it indicates  that branch usage is solar energy,
                If the enumeration value is 6, it indicates  that branch usage is DC D.G.,
                If the enumeration value is 7, it indicates  that branch usage is power cascade,
                If the enumeration value is 8, it indicates  that branch usage is other,
                If the enumeration value is 9, it indicates  that branch usage is LLVD1 Load,
                If the enumeration value is 10, it indicates  that branch usage is LLVD2 Load,
                If the enumeration value is 11, it indicates  that branch usage is LLVD3 Load,
                If the enumeration value is 12, it indicates  that branch usage is LLVD4 Load,
                  If the enumeration value is 255, that battery operation status unknown."
            ::= { hwIcbdGeneralEntry 5 }

        hwIcbdGeneralRatedCapacity OBJECT-TYPE
            SYNTAX Unsigned32 (0..1250)
            MAX-ACCESS read-only
            STATUS current
            DESCRIPTION
                "ICBD general rated capacity, 
                Value range:0 to 125.0.
                Unit: A.
                and the value is accurate to one decimal space (.1). 
                If the value is 2147483647(0x7FFFFFFF), it indicates that the value is invalid."
            ::= { hwIcbdGeneralEntry 6 }

        hwIcbdGeneralCurrent OBJECT-TYPE
            SYNTAX Integer32 ( -30000..30000)
            MAX-ACCESS read-only
            STATUS current
            DESCRIPTION
                "IDBD general current. It is an analog parameter collected by the IDBD general in real time. Value range: -3000 to +3000, unit: A, and the value is accurate to one decimal place (.1).  If the value is 2147483647(0x7FFFFFFF), it indicates that the value is invalid."
            ::= { hwIcbdGeneralEntry 7 }

        hwIcbdGeneralTotalInputEnergy OBJECT-TYPE
            SYNTAX Unsigned32 (0..4294967295)
            MAX-ACCESS read-only
            STATUS current
            DESCRIPTION
                "ICBD general total input energy, 
                Value range:0 to 4294967295.
                Unit: kWh.
                and the value is accurate to two decimal space (.01). "
            ::= { hwIcbdGeneralEntry 8 }

        hwIcbdGeneralOCThreshold OBJECT-TYPE
            SYNTAX Unsigned32 (0..20000)
            MAX-ACCESS read-write
            STATUS current
            DESCRIPTION
                "ICBD general overcurrent threshold, 
                Value range:0 to 2000.0.
                Unit: A.
                and the value is accurate to two decimal space (.1). "
            ::= { hwIcbdGeneralEntry 10 }

        hwIcbdGeneralEnbManualCtrl OBJECT-TYPE
            SYNTAX INTEGER
                {
                disable(1),
                enable(2),
                unknown(255)
                }
            MAX-ACCESS read-write
            STATUS current
            DESCRIPTION
                "State of the ICBD general enable manual On/Off control.It is an enumeration type:
                If the enumeration value is 1, it indicates that manual On/Off control is disable,
                If the enumeration value is 2,it indicates that manual On/Off control is enable,
                If the enumeration value is 255, it indicates that manual On/Off control is unknown."
            ::= { hwIcbdGeneralEntry 11 }

        hwIcbdGeneralTotalOutputEnergy OBJECT-TYPE
            SYNTAX Unsigned32 (0..4294967295)
            MAX-ACCESS read-only
            STATUS current
            DESCRIPTION
                "ICBD general total output energy, 
                Value range:0 to 4294967295.
                Unit: kWh.
                and the value is accurate to two decimal space (.01). "
            ::= { hwIcbdGeneralEntry 12 }

        hwIcbdGeneralDCVolt OBJECT-TYPE
            SYNTAX Unsigned32 (0..1000)
            MAX-ACCESS read-only
            STATUS current
            DESCRIPTION
                "IDBD general DC voltage. It is an analog parameter collected by the IDBD load in real time. Value range: 0 to 100, unit: V, and the value is accurate to one decimal place (.1).  If the value is 2147483647(0x7FFFFFFF), it indicates that the value is invalid."
            ::= { hwIcbdGeneralEntry 13 }

        hwIcbdGeneralTemperature OBJECT-TYPE
            SYNTAX Integer32 (-1000..1000)
            MAX-ACCESS read-only
            STATUS current
            DESCRIPTION
                "ICBD general temperature. 
                Value range:-100 to 100，unit: ℃, the value is accurate to one decimal space (.1). "
            ::= { hwIcbdGeneralEntry 14 }

        hwIcbdLoad OBJECT IDENTIFIER ::= { hwSiteIcbd 2 }

        hwIcbdLoadSampTable OBJECT-TYPE
            SYNTAX SEQUENCE OF HwIcbdLoadSampEntry
            MAX-ACCESS not-accessible
             STATUS current
             DESCRIPTION
                ""
            ::= { hwIcbdLoad 1 }

        hwIcbdLoadSampEntry OBJECT-TYPE
                        SYNTAX HwIcbdLoadSampEntry
            MAX-ACCESS not-accessible
             STATUS current
             DESCRIPTION
                ""
            INDEX { hwIcbdLoadEquipIndex }
            ::= { hwIcbdLoadSampTable 1 }

        HwIcbdLoadSampEntry            ::= SEQUENCE {
                hwIcbdLoadEquipIndex
                    Unsigned32,
                hwIcbdLoadEquipId
                    Unsigned32,
                hwIcbdLoadEquipName
                    OCTET STRING,
                hwIcbdLoadFatherEquipName
                    OCTET STRING,
                hwIcbdLoadBranchUsage
                    INTEGER,
                hwIcbdLoadRatedCapacity
                    Unsigned32,
                hwIcbdLoadCurrent
                    Integer32,
                hwIcbdLoadPower
                    Unsigned32,
                hwIcbdLoadTotalDCEnergyConsumption
                    Unsigned32,
                hwIcbdLoadDisconnectReason
                    INTEGER,
                hwIcbdLoadDcVolt
                    Unsigned32,
                hwIcbdLoadTemperature
                    Integer32
            }

        hwIcbdLoadEquipIndex OBJECT-TYPE
            SYNTAX Unsigned32
            MAX-ACCESS read-only
            STATUS current
            DESCRIPTION
                "ICBD load table index. Lines of the device list are restricted by the quantity of ICBD load."
            ::= { hwIcbdLoadSampEntry 1 }

        hwIcbdLoadEquipId OBJECT-TYPE
            SYNTAX Unsigned32
            MAX-ACCESS read-only
            STATUS current
            DESCRIPTION
                "ICBD load device ID."
            ::= { hwIcbdLoadSampEntry 2 }

        hwIcbdLoadEquipName OBJECT-TYPE
            SYNTAX OCTET STRING (SIZE (0..63))
            MAX-ACCESS read-only
            STATUS current
            DESCRIPTION
                "ICBD load name, of the character string type, is used to specify ICBD load.
                
                "
            ::= { hwIcbdLoadSampEntry 3 }

        hwIcbdLoadFatherEquipName OBJECT-TYPE
            SYNTAX OCTET STRING (SIZE (0..63))
            MAX-ACCESS read-only
            STATUS current
            DESCRIPTION
                "ICBD load father equip name, of the character string type, is used to specify ICBD load father equip.
                "
            ::= { hwIcbdLoadSampEntry 4 }

        hwIcbdLoadBranchUsage OBJECT-TYPE
            SYNTAX INTEGER
                {
                blvdLoad(1),
                customizedLoad(2),
                llvd1Load(3),
                llvd2Load(4),
                llvd3Load(5),
                llvd4Load(6),
                unknown(255)
                }
            MAX-ACCESS read-only
            STATUS current
            DESCRIPTION
                "State of the ICBD load branch usage.It is an enumeration type:
                If the enumeration value is 1, it indicates that branch usage is blvd Load,
                If the enumeration value is 2,it indicates that branch usage is customized load,
                If the enumeration value is 3, it indicates that branch usage is LLVD1 Load,
                If the enumeration value is 4, it indicates that branch usage is LLVD2 Load,
                If the enumeration value is 5, it indicates that branch usage is LLVD3 Load,
                If the enumeration value is 6, it indicates that branch usage is LLVD4 Load,
                If the enumeration value is 255, that battery operation status unknown."
            ::= { hwIcbdLoadSampEntry 5 }

        hwIcbdLoadRatedCapacity OBJECT-TYPE
            SYNTAX Unsigned32 (0..1250)
            MAX-ACCESS read-only
            STATUS current
            DESCRIPTION
                "ICBD load rated capacity, 
                Value range:0 to 125.0.
                Unit: A.
                and the value is accurate to one decimal space (.1). 
                If the value is 2147483647(0x7FFFFFFF), it indicates that the value is invalid."
            ::= { hwIcbdLoadSampEntry 6 }

        hwIcbdLoadCurrent OBJECT-TYPE
            SYNTAX Integer32 (-30000..30000)
            MAX-ACCESS read-only
            STATUS current
            DESCRIPTION
                "IDBD load current. It is an analog parameter collected by the IDBD load in real time. Value range: -30000 to +3000, unit: A, and the value is accurate to one decimal place (.1).  If the value is 2147483647(0x7FFFFFFF), it indicates that the value is invalid."
            ::= { hwIcbdLoadSampEntry 7 }

        hwIcbdLoadPower OBJECT-TYPE
            SYNTAX Unsigned32 (0..300000)
            MAX-ACCESS read-only
            STATUS current
            DESCRIPTION
                "ICBD load power, 
                Value range:0 to 3000.00.
                Unit: kWh.
                and the value is accurate to two decimal space (.01). "
            ::= { hwIcbdLoadSampEntry 8 }

        hwIcbdLoadTotalDCEnergyConsumption OBJECT-TYPE
            SYNTAX Unsigned32 (0..4294967295)
            MAX-ACCESS read-only
            STATUS current
            DESCRIPTION
                "ICBD load total DC energy consumption, 
                Value range:0 to 4294967295.
                Unit: kWh.
                and the value is accurate to two decimal space (.01). "
            ::= { hwIcbdLoadSampEntry 9 }

        hwIcbdLoadDisconnectReason OBJECT-TYPE
            SYNTAX INTEGER
                {
                connect(1),
                lowVoltDiscon(2),
                timeDisconnect(3),
                capacityDisconnect(4),
                highTempDisconnect(5),
                manualDisconnect(6),
                timedDisconnect(7),
                maintDisconnect(8),
                peakShavingDiscon(9),
                dinDisconnect(10),
                ldDiscon-EnergyCons(11),
                noBkupInExemptPeriod(12),
                unauthorizedDiscon(13),
                dgServiceNotPurchased(14),
                liBattOverloadDiscon(15),
                backupResReservDiscon(16),
                lowTempDiscon(17),
                ultraLowTempDiscon(18),
                unknown(255)
                }
            MAX-ACCESS read-only
            STATUS current
            DESCRIPTION
                "State of the ICBD load disconnect reason.It is an enumeration type:
                If the enumeration value is 1, it indicates that load is connect,
                If the enumeration value is 2,it indicates that reason is LVD,
                If the enumeration value is 3, it indicates that reason is time disconnect,
                If the enumeration value is 4, , it indicates that reason is cap disconnect,
                If the enumeration value is 5, it indicates  that reason is HT disconnect,
                If the enumeration value is 6, it indicates  that reason is manual disconnect,
                If the enumeration value is 7, it indicates  that reason is timed disconnect,
                If the enumeration value is 8, it indicates  that reason is maintenance disconnect,
                If the enumeration value is 9, it indicates  that reason is peak shave disconnect,
                If the enumeration value is 10, it indicates  that reason is DIN disconnect,
                If the enumeration value is 11, it indicates  that reason is LdDiscon-EnergyCons,
                If the enumeration value is 12, it indicates  that reason is NoBkupInExemptPeriod,
                If the enumeration value is 13, it indicates  that reason is UnauthorizedDiscon,
                If the enumeration value is 14, it indicates  that reason is DGServiceNotPurchased,
                If the enumeration value is 15, it indicates  that reason is LiBattOverloadDiscon,
                If the enumeration value is 16, it indicates  that reason is BackupResReservDiscon,
                If the enumeration value is 17, it indicates  that reason is LowTempDiscon,
                If the enumeration value is 18, it indicates  that reason is UltraLowTempDiscon,
                If the enumeration value is 255, that battery operation status unknown."
            ::= { hwIcbdLoadSampEntry 10 }

        hwIcbdLoadDcVolt OBJECT-TYPE
            SYNTAX Unsigned32 (0..1000)
            MAX-ACCESS read-only
            STATUS current
            DESCRIPTION
                "IDBD load DC voltage. It is an analog parameter collected by the IDBD load in real time. Value range: 0 to 100, unit: V, and the value is accurate to one decimal place (.1).  If the value is 2147483647(0x7FFFFFFF), it indicates that the value is invalid."
            ::= { hwIcbdLoadSampEntry 11 }

        hwIcbdLoadTemperature OBJECT-TYPE
            SYNTAX Integer32 (-1000..1000)
            MAX-ACCESS read-only
            STATUS current
            DESCRIPTION
                "ICBD load temperature. 
                Value range:-100 to 100，unit: ℃, the value is accurate to one decimal space (.1). "
            ::= { hwIcbdLoadSampEntry 12 }

        hwIcbdLoadSetTable OBJECT-TYPE
            SYNTAX SEQUENCE OF HwIcbdLoadSetEntry
            MAX-ACCESS not-accessible
             STATUS current
             DESCRIPTION
                ""
            ::= { hwIcbdLoad 2 }

        hwIcbdLoadSetEntry OBJECT-TYPE
                        SYNTAX HwIcbdLoadSetEntry
            MAX-ACCESS not-accessible
             STATUS current
             DESCRIPTION
                ""
            INDEX { hwIcbdLoadEnablePlanDisconnect }
            ::= { hwIcbdLoadSetTable 1 }

        HwIcbdLoadSetEntry            ::= SEQUENCE {
                hwIcbdLoadEnablePlanDisconnect
                    INTEGER,
                hwIcbdLoadPDStartTime1
                    OCTET STRING,
                hwIcbdLoadPDDuration1
                    Unsigned32,
                hwIcbdLoadPDStartTime2
                    OCTET STRING,
                hwIcbdLoadPDDuration2
                    Unsigned32,
                hwIcbdLoadPDStartTime3
                    OCTET STRING,
                hwIcbdLoadPDDuration3
                    Unsigned32,
                hwIcbdLoadPDStartTime4
                    OCTET STRING,
                hwIcbdLoadPDDuration4
                    Unsigned32,
                hwIcbdLoadPDStartTime5
                    OCTET STRING,
                hwIcbdLoadPDDuration5
                    Unsigned32,
                hwIcbdLoadExemptPeriodNoBk
                    INTEGER,
                hwIcbdLoadExemptStartTime1
                    OCTET STRING,
                hwIcbdLoadExemptDuration1
                    Unsigned32,
                hwIcbdLoadExemptStartTime2
                    OCTET STRING,
                hwIcbdLoadExemptDuration2
                    Unsigned32,
                hwIcbdLoadExemptStartTime3
                    OCTET STRING,
                hwIcbdLoadExemptDuration3
                    Unsigned32,
                hwIcbdLoadExemptStartTime4
                    OCTET STRING,
                hwIcbdLoadExemptDuration4
                    Unsigned32,
                hwIcbdLoadExemptStartTime5
                    OCTET STRING,
                hwIcbdLoadExemptDuration5
                    Unsigned32,
                hwIcbdLoadDisconCons
                    Unsigned32,
                hwIcbdLoadEnbManualCtrl
                    INTEGER,
                hwIcbdLoadOvercurrentThreshold
                    Unsigned32,
                hwIcbdLoadBranchOnOffControl
                    INTEGER,
                hwIcbdLoadEnableLoadDisconnect
                    INTEGER,
                hwIcbdLoadDisconnectMode
                    INTEGER,
                hwIcbdLoadDisconnectVoltage
                    Unsigned32,
                hwIcbdLoadReconnectionVoltage
                    Unsigned32,
                hwIcbdLoadDisconnectTime
                    Unsigned32,
                hwIcbdLoadDisconnectCapacity
                    Unsigned32,
                hwIcbdLoadEnableHighTempDisconnect
                    INTEGER,
                hwIcbdLoadDisconnectTemperature
                    Unsigned32,
                hwIcbdLoadUserConfig
                    INTEGER,
                hwIcbdLoadEnableDisconnectPeakShaving
                    INTEGER,
                hwIcbdLoadSetDGOff
                    INTEGER,
                hwIcbdLoadBranchName
                    OCTET STRING
            }

        hwIcbdLoadEnablePlanDisconnect OBJECT-TYPE
            SYNTAX INTEGER
                {
                disable(1),
                enable(2),
                unknown(255)
                }
            MAX-ACCESS read-write
            STATUS current
            DESCRIPTION
                "State of the ICBD load enable plan disconnect.It is an enumeration type:
                If the enumeration value is 1, it indicates that plan disconnect is disable,
                If the enumeration value is 2,it indicates that that plan disconnect is enable,
                  If the enumeration value is 255, that plan disconnect status unknown."
            ::= { hwIcbdLoadSetEntry 1 }

        hwIcbdLoadPDStartTime1 OBJECT-TYPE
            SYNTAX OCTET STRING (SIZE (0..60))
            MAX-ACCESS read-write
            STATUS current
            DESCRIPTION
                "Icbd load plan disconnect start time1."
            ::= { hwIcbdLoadSetEntry 2 }

        hwIcbdLoadPDDuration1 OBJECT-TYPE
            SYNTAX Unsigned32 (0..1440)
            MAX-ACCESS read-write
            STATUS current
            DESCRIPTION
                "Icbd load plan disconnect duration1."
            ::= { hwIcbdLoadSetEntry 3 }

        hwIcbdLoadPDStartTime2 OBJECT-TYPE
            SYNTAX OCTET STRING (SIZE (0..60))
            MAX-ACCESS read-write
            STATUS current
            DESCRIPTION
                "Icbd load plan disconnect start time2."
            ::= { hwIcbdLoadSetEntry 4 }

        hwIcbdLoadPDDuration2 OBJECT-TYPE
            SYNTAX Unsigned32 (0..1440)
            MAX-ACCESS read-write
            STATUS current
            DESCRIPTION
                "Icbd load plan disconnect duration2."
            ::= { hwIcbdLoadSetEntry 5 }

        hwIcbdLoadPDStartTime3 OBJECT-TYPE
            SYNTAX OCTET STRING (SIZE (0..60))
            MAX-ACCESS read-write
            STATUS current
            DESCRIPTION
                "Icbd load plan disconnect start time3."
            ::= { hwIcbdLoadSetEntry 6 }

        hwIcbdLoadPDDuration3 OBJECT-TYPE
            SYNTAX Unsigned32 (0..1440)
            MAX-ACCESS read-write
            STATUS current
            DESCRIPTION
                "Icbd load plan disconnect duration3."
            ::= { hwIcbdLoadSetEntry 7 }

        hwIcbdLoadPDStartTime4 OBJECT-TYPE
            SYNTAX OCTET STRING (SIZE (0..60))
            MAX-ACCESS read-write
            STATUS current
            DESCRIPTION
                "Icbd load plan disconnect start time4."
            ::= { hwIcbdLoadSetEntry 8 }

        hwIcbdLoadPDDuration4 OBJECT-TYPE
            SYNTAX Unsigned32 (0..1440)
            MAX-ACCESS read-write
            STATUS current
            DESCRIPTION
                "Icbd load plan disconnect duration4."
            ::= { hwIcbdLoadSetEntry 9 }

        hwIcbdLoadPDStartTime5 OBJECT-TYPE
            SYNTAX OCTET STRING (SIZE (0..60))
            MAX-ACCESS read-write
            STATUS current
            DESCRIPTION
                "Icbd load plan disconnect start time5."
            ::= { hwIcbdLoadSetEntry 10 }

        hwIcbdLoadPDDuration5 OBJECT-TYPE
            SYNTAX Unsigned32 (0..1440)
            MAX-ACCESS read-write
            STATUS current
            DESCRIPTION
                "Icbd load plan disconnect duration5."
            ::= { hwIcbdLoadSetEntry 11 }

        hwIcbdLoadExemptPeriodNoBk OBJECT-TYPE
            SYNTAX INTEGER
                {
                disable(1),
                enable(2),
                unknown(255)
                }
            MAX-ACCESS read-write
            STATUS current
            DESCRIPTION
                "State of the ICBD load exempt period no backup .It is an enumeration type:
                If the enumeration value is 1, it indicates that exempt period no backup is disable,
                If the enumeration value is 2, it indicates that exempt period no backup is enable,
                  If the enumeration value is 255, that status unknown."
            ::= { hwIcbdLoadSetEntry 12 }

        hwIcbdLoadExemptStartTime1 OBJECT-TYPE
            SYNTAX OCTET STRING (SIZE (0..60))
            MAX-ACCESS read-write
            STATUS current
            DESCRIPTION
                "Icbd load exempt start time1."
            ::= { hwIcbdLoadSetEntry 13 }

        hwIcbdLoadExemptDuration1 OBJECT-TYPE
            SYNTAX Unsigned32 (0..1440)
            MAX-ACCESS read-write
            STATUS current
            DESCRIPTION
                "Icbd load exempt duration1."
            ::= { hwIcbdLoadSetEntry 14 }

        hwIcbdLoadExemptStartTime2 OBJECT-TYPE
            SYNTAX OCTET STRING (SIZE (0..60))
            MAX-ACCESS read-write
            STATUS current
            DESCRIPTION
                "Icbd load exempt start time2."
            ::= { hwIcbdLoadSetEntry 15 }

        hwIcbdLoadExemptDuration2 OBJECT-TYPE
            SYNTAX Unsigned32 (0..1440)
            MAX-ACCESS read-write
            STATUS current
            DESCRIPTION
                "Icbd load exempt duration2."
            ::= { hwIcbdLoadSetEntry 16 }

        hwIcbdLoadExemptStartTime3 OBJECT-TYPE
            SYNTAX OCTET STRING (SIZE (0..60))
            MAX-ACCESS read-write
            STATUS current
            DESCRIPTION
                "Icbd load exempt start time3."
            ::= { hwIcbdLoadSetEntry 17 }

        hwIcbdLoadExemptDuration3 OBJECT-TYPE
            SYNTAX Unsigned32 (0..1440)
            MAX-ACCESS read-write
            STATUS current
            DESCRIPTION
                "Icbd load exempt duration3."
            ::= { hwIcbdLoadSetEntry 18 }

        hwIcbdLoadExemptStartTime4 OBJECT-TYPE
            SYNTAX OCTET STRING (SIZE (0..60))
            MAX-ACCESS read-write
            STATUS current
            DESCRIPTION
                "Icbd load exempt start time4."
            ::= { hwIcbdLoadSetEntry 19 }

        hwIcbdLoadExemptDuration4 OBJECT-TYPE
            SYNTAX Unsigned32 (0..1440)
            MAX-ACCESS read-write
            STATUS current
            DESCRIPTION
                "Icbd load exempt duration4."
            ::= { hwIcbdLoadSetEntry 20 }

        hwIcbdLoadExemptStartTime5 OBJECT-TYPE
            SYNTAX OCTET STRING (SIZE (0..60))
            MAX-ACCESS read-write
            STATUS current
            DESCRIPTION
                "Icbd load exempt start time5."
            ::= { hwIcbdLoadSetEntry 21 }

        hwIcbdLoadExemptDuration5 OBJECT-TYPE
            SYNTAX Unsigned32 (0..1440)
            MAX-ACCESS read-write
            STATUS current
            DESCRIPTION
                "Icbd load exempt duration5."
            ::= { hwIcbdLoadSetEntry 22 }

        hwIcbdLoadDisconCons OBJECT-TYPE
            SYNTAX Unsigned32 (0..10000000)
            MAX-ACCESS read-write
            STATUS current
            DESCRIPTION
                "Icbd load disconnect consumption."
            ::= { hwIcbdLoadSetEntry 23 }

        hwIcbdLoadEnbManualCtrl OBJECT-TYPE
            SYNTAX INTEGER
                {
                disable(1),
                enable(2),
                unknown(255)
                }
            MAX-ACCESS read-write
            STATUS current
            DESCRIPTION
                "State of the ICBD load manual control .It is an enumeration type:
                If the enumeration value is 1, it indicates that manual control is disable,
                If the enumeration value is 2, it indicates that manual control is enable,
                  If the enumeration value is 255, that status unknown."
            ::= { hwIcbdLoadSetEntry 24 }

        hwIcbdLoadOvercurrentThreshold OBJECT-TYPE
            SYNTAX Unsigned32 (30..20000)
            MAX-ACCESS read-write
            STATUS current
            DESCRIPTION
                "Icbd load over current threshold."
            ::= { hwIcbdLoadSetEntry 26 }

        hwIcbdLoadBranchOnOffControl OBJECT-TYPE
            SYNTAX INTEGER
                {
                
                off(1),
                on(2),
                unknown(255)
                }
            MAX-ACCESS read-write
            STATUS current
            DESCRIPTION
                "State of the ICBD load on/off control.It is an enumeration type:
                If the enumeration value is 1, it indicates that branch is off,
                If the enumeration value is 2, it indicates that branch is on,
                  If the enumeration value is 255, that status unknown."
            ::= { hwIcbdLoadSetEntry 27 }

        hwIcbdLoadEnableLoadDisconnect OBJECT-TYPE
            SYNTAX INTEGER
                {
                
                disable(1),
                enable(2),
                unknown(255)
                }
            MAX-ACCESS read-write
            STATUS current
            DESCRIPTION
                "State of the ICBD load disconnect.It is an enumeration type:
                If the enumeration value is 1, it indicates that load disconnect is disable,
                If the enumeration value is 2, it indicates that load disconnect is enable,
                  If the enumeration value is 255, that status unknown."
            ::= { hwIcbdLoadSetEntry 28 }

        hwIcbdLoadDisconnectMode OBJECT-TYPE
            SYNTAX INTEGER
                {
                voltageMode(1),
                timingMode(2),
                capacityMode(3),
                consumptionMode(4)
                }
            MAX-ACCESS read-write
            STATUS current
            DESCRIPTION
                "State of the ICBD load disconnect mode.It is an enumeration type:
                If the enumeration value is 1, it indicates that load disconnect mode is voltageMode,
                If the enumeration value is 2, it indicates that load disconnect mode is timingMode,
                If the enumeration value is 3, it indicates that load disconnect mode is capacityMode,
                If the enumeration value is 4, it indicates that load disconnect mode is consumptionMode,
                  If the enumeration value is 255, that status unknown."
            ::= { hwIcbdLoadSetEntry 29 }

        hwIcbdLoadDisconnectVoltage OBJECT-TYPE
            SYNTAX Unsigned32 (3600..5600)
            MAX-ACCESS read-write
            STATUS current
            DESCRIPTION
                "Icbd load disconnect voltage."
            ::= { hwIcbdLoadSetEntry 30 }

        hwIcbdLoadReconnectionVoltage OBJECT-TYPE
            SYNTAX Unsigned32 (3700..5800)
            MAX-ACCESS read-write
            STATUS current
            DESCRIPTION
                "Icbd load redisconnect voltage."
            ::= { hwIcbdLoadSetEntry 31 }

        hwIcbdLoadDisconnectTime OBJECT-TYPE
            SYNTAX Unsigned32 (0..1440)
            MAX-ACCESS read-write
            STATUS current
            DESCRIPTION
                "Icbd load disconnect time."
            ::= { hwIcbdLoadSetEntry 32 }

        hwIcbdLoadDisconnectCapacity OBJECT-TYPE
            SYNTAX Unsigned32 (0..99)
            MAX-ACCESS read-write
            STATUS current
            DESCRIPTION
                "Icbd load disconnect capacity."
            ::= { hwIcbdLoadSetEntry 33 }

        hwIcbdLoadEnableHighTempDisconnect OBJECT-TYPE
            SYNTAX INTEGER
                {
                
                disable(1),
                enable(2),
                unknown(255)
                }
            MAX-ACCESS read-write
            STATUS current
            DESCRIPTION
                "State of the ICBD load high temperature disconnect.It is an enumeration type:
                If the enumeration value is 1, it indicates that load disconnect mode is disable,
                If the enumeration value is 2, it indicates that load disconnect mode is enable,
                  If the enumeration value is 255, that status unknown."
            ::= { hwIcbdLoadSetEntry 34 }

        hwIcbdLoadDisconnectTemperature OBJECT-TYPE
            SYNTAX Unsigned32 (2500..8000)
            MAX-ACCESS read-write
            STATUS current
            DESCRIPTION
                "Icbd load disconnect temperature."
            ::= { hwIcbdLoadSetEntry 35 }

        hwIcbdLoadUserConfig OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "Icbd load user config, It is an enumeration type."
            ::= { hwIcbdLoadSetEntry 36 }

        hwIcbdLoadEnableDisconnectPeakShaving OBJECT-TYPE
            SYNTAX INTEGER
                {
                
                no(1),
                yes(2),
                unknown(255)
                }
            MAX-ACCESS read-write
            STATUS current
            DESCRIPTION
                "State of the ICBD load peak shaving disconnect .It is an enumeration type:
                If the enumeration value is 1, it indicates that peak shaving disconnect is disable,
                If the enumeration value is 2, it indicates that peak shaving disconnect is enable,
                  If the enumeration value is 255, that status unknown."
            ::= { hwIcbdLoadSetEntry 38 }

        hwIcbdLoadSetDGOff OBJECT-TYPE
            SYNTAX INTEGER
                {
                disable(1),
                enable(2),
                unknown(255)
                }
            MAX-ACCESS read-write
            STATUS current
            DESCRIPTION
                "State of the ICBD load DG off .It is an enumeration type:
                If the enumeration value is 1, it indicates that peak shaving disconnect is disable,
                If the enumeration value is 2, it indicates that peak shaving disconnect is enable,
                  If the enumeration value is 255, that status unknown."
            ::= { hwIcbdLoadSetEntry 39 }

        hwIcbdLoadBranchName OBJECT-TYPE
            SYNTAX OCTET STRING (SIZE (0..100))
            MAX-ACCESS read-write
            STATUS current
            DESCRIPTION
                "Icbd load distribution unit name."
            ::= { hwIcbdLoadSetEntry 40 }

        hwIcbdGroup OBJECT IDENTIFIER ::= { hwSiteIcbd 3 }

        hwIcbdGroupSampTable OBJECT-TYPE
            SYNTAX SEQUENCE OF HwIcbdGroupSampEntry
            MAX-ACCESS not-accessible
             STATUS current
             DESCRIPTION
                ""
            ::= { hwIcbdGroup 1 }

        hwIcbdGroupSampEntry OBJECT-TYPE
                        SYNTAX HwIcbdGroupSampEntry
            MAX-ACCESS not-accessible
             STATUS current
             DESCRIPTION
                ""
            INDEX { hwIcbdGroupEquipIndex }
            ::= { hwIcbdGroupSampTable 1 }

        HwIcbdGroupSampEntry            ::= SEQUENCE {
                hwIcbdGroupEquipIndex
                    Unsigned32,
                hwIcbdGroupEquipId
                    Unsigned32,
                hwIcbdGroupEquipName
                    OCTET STRING,
                hwIcbdGroupFatherEquipName
                    OCTET STRING,
                hwIcbdGroupDcLoadTotalEnergyConsumption
                    Unsigned32,
                hwIcbdGroupIcbdNum
                    Unsigned32,
                hwIcbdGroupCommNormalIcbdNum
                    Unsigned32,
                hwIcbdGroupTotalLoadCurr
                    Unsigned32,
                hwIcbdGroupTotalLoadPower
                    Unsigned32,
                hwIcbdGroupSoftwareVersion
                    OCTET STRING,
                hwIcbdGroupHardwareVersion
                    OCTET STRING
            }

        hwIcbdGroupEquipIndex OBJECT-TYPE
            SYNTAX Unsigned32
            MAX-ACCESS read-only
            STATUS current
            DESCRIPTION
                "ICBD group table index. Lines of the device list are restricted by the quantity of ICBD group."
            ::= { hwIcbdGroupSampEntry 1 }

        hwIcbdGroupEquipId OBJECT-TYPE
            SYNTAX Unsigned32
            MAX-ACCESS read-only
            STATUS current
            DESCRIPTION
                "ICBD group device ID."
            ::= { hwIcbdGroupSampEntry 2 }

        hwIcbdGroupEquipName OBJECT-TYPE
            SYNTAX OCTET STRING (SIZE (0..63))
            MAX-ACCESS read-only
            STATUS current
            DESCRIPTION
                "ICBD group name, of the character string type, is used to specify ICBD group.
                
                "
            ::= { hwIcbdGroupSampEntry 3 }

        hwIcbdGroupFatherEquipName OBJECT-TYPE
            SYNTAX OCTET STRING (SIZE (0..63))
            MAX-ACCESS read-only
            STATUS current
            DESCRIPTION
                "ICBD group father equip name, of the character string type, is used to specify ICBD group father equip.
                "
            ::= { hwIcbdGroupSampEntry 4 }

        hwIcbdGroupDcLoadTotalEnergyConsumption OBJECT-TYPE
            SYNTAX Unsigned32 (0..4294967295)
            MAX-ACCESS read-only
            STATUS current
            DESCRIPTION
                "ICBD group total DC energy consumption, 
                Value range:0 to 4294967295.
                Unit: kWh.
                and the value is accurate to two decimal space (.01). "
            ::= { hwIcbdGroupSampEntry 5 }

        hwIcbdGroupIcbdNum OBJECT-TYPE
            SYNTAX Unsigned32 (0..65535)
            MAX-ACCESS read-only
            STATUS current
            DESCRIPTION
                "IDMU Total iCBDs."
            ::= { hwIcbdGroupSampEntry 6 }

        hwIcbdGroupCommNormalIcbdNum OBJECT-TYPE
            SYNTAX Unsigned32 (0..65535)
            MAX-ACCESS read-only
            STATUS current
            DESCRIPTION
                "IDMU Total iCBDs Communicating Normally."
            ::= { hwIcbdGroupSampEntry 7 }

        hwIcbdGroupTotalLoadCurr OBJECT-TYPE
            SYNTAX Unsigned32 (0..300000)
            MAX-ACCESS read-only
            STATUS current
            DESCRIPTION
                "IDMU total DC load current. Value range: 0 to 30000, unit: A."
            ::= { hwIcbdGroupSampEntry 8 }

        hwIcbdGroupTotalLoadPower OBJECT-TYPE
            SYNTAX Unsigned32 (0..300000)
            MAX-ACCESS read-only
            STATUS current
            DESCRIPTION
                "IDMU Total DC load power. Value range: 0 to 3000, unit: kW."
            ::= { hwIcbdGroupSampEntry 9 }

        hwIcbdGroupSoftwareVersion OBJECT-TYPE
            SYNTAX OCTET STRING (SIZE (0..100))
            MAX-ACCESS read-only
            STATUS current
            DESCRIPTION
                "IDMU software version."
            ::= { hwIcbdGroupSampEntry 10 }

        hwIcbdGroupHardwareVersion OBJECT-TYPE
            SYNTAX OCTET STRING (SIZE (0..100))
            MAX-ACCESS read-only
            STATUS current
            DESCRIPTION
                "IDMU hardware version."
            ::= { hwIcbdGroupSampEntry 11 }

        hwSiteSSM OBJECT IDENTIFIER ::= { hwSiteMonitorMIBObjects 51 }

        hwSSMGroupEquip OBJECT IDENTIFIER ::= { hwSiteSSM 1 }

        hwSSMGroupSampTable OBJECT-TYPE
            SYNTAX SEQUENCE OF HwSSMGroupSampEntry
            MAX-ACCESS not-accessible
             STATUS current
             DESCRIPTION
                ""
            ::= { hwSSMGroupEquip 1 }

        hwSSMGroupSampEntry OBJECT-TYPE
                        SYNTAX HwSSMGroupSampEntry
            MAX-ACCESS not-accessible
             STATUS current
             DESCRIPTION
                ""
            INDEX { hwSSMGroupIndex }
            ::= { hwSSMGroupSampTable 1 }

        HwSSMGroupSampEntry            ::= SEQUENCE {
                hwSSMGroupIndex
                    Unsigned32,
                hwSSMGroupEquipId
                    Unsigned32,
                hwSSMGroupEquipName
                    OCTET STRING,
                hwSSMGroupOutputVolt
                    Unsigned32,
                hwSSMGroupLoadCurrent
                    Integer32,
                hwSSMGroupPVTotalOutputPower
                    Unsigned32,
                hwSSMGroupBatVolt
                    Unsigned32,
                hwSSMGroupBatCurr
                    Integer32,
                hwSSMGroupTotalCapacity
                    Unsigned32,
                hwSSMGroupTotalRemainCapacity
                    Unsigned32,
                hwSSMGroupTemperature
                    Integer32,
                hwSSMGroupTotalDisChargePower
                    Unsigned32,
                hwSSMGroupEsmuCommNum
                    Unsigned32
            }

        hwSSMGroupIndex OBJECT-TYPE
            SYNTAX Unsigned32
            MAX-ACCESS read-only
            STATUS current
            DESCRIPTION
                "SSM group table index. Lines of the device list are restricted by the quantity of SSM group."
            ::= { hwSSMGroupSampEntry 1 }

        hwSSMGroupEquipId OBJECT-TYPE
            SYNTAX Unsigned32
            MAX-ACCESS read-only
            STATUS current
            DESCRIPTION
                "SSM group device ID."
            ::= { hwSSMGroupSampEntry 2 }

        hwSSMGroupEquipName OBJECT-TYPE
            SYNTAX OCTET STRING (SIZE (0..63))
            MAX-ACCESS read-only
            STATUS current
            DESCRIPTION
                "SSM group name, of the character string type, is used to specify SSM group.
                
                "
            ::= { hwSSMGroupSampEntry 3 }

        hwSSMGroupOutputVolt OBJECT-TYPE
            SYNTAX Unsigned32 (0..600)
            MAX-ACCESS read-only
            STATUS current
            DESCRIPTION
                "DC output voltage: 0.0 to 60.0, unit: V, and the value is two decimal space (.1). If the value is 2147483647(0x7FFFFFFF), it indicates that the value is invalid."
            ::= { hwSSMGroupSampEntry 4 }

        hwSSMGroupLoadCurrent OBJECT-TYPE
            SYNTAX Integer32 (-2000..2000)
            MAX-ACCESS read-only
            STATUS current
            DESCRIPTION
                "Load current: -200.0 to 200.0, 
                unit: A, 
                and the value is one decimal space (.1). If the value is 2147483647(0x7FFFFFFF), it indicates that the value is invalid."
            ::= { hwSSMGroupSampEntry 5 }

        hwSSMGroupPVTotalOutputPower OBJECT-TYPE
            SYNTAX Unsigned32 (0..4294967295)
            MAX-ACCESS read-only
            STATUS current
            DESCRIPTION
                "Total PV output power; 
                Value range: 0 to 4294967295, 
                and the value is accurate to one decimal place (.01), 
                If the value is 2147483647(0x7FFFFFFF), it indicates that the value is invalid."
            ::= { hwSSMGroupSampEntry 6 }

        hwSSMGroupBatVolt OBJECT-TYPE
            SYNTAX Unsigned32 (0..1000)
            MAX-ACCESS read-only
            STATUS current
            DESCRIPTION
                "The battery volt; Value range: 0 to 100, 
                unit: V. 
                and the value is accurate to one decimal place (.1).  
                If the value is 2147483647(0x7FFFFFFF), it indicates that the value is invalid."
            ::= { hwSSMGroupSampEntry 7 }

        hwSSMGroupBatCurr OBJECT-TYPE
            SYNTAX Integer32 (-40000..40000)
            MAX-ACCESS read-only
            STATUS current
            DESCRIPTION
                "The battery current; Value range: -400 to 400, 
                unit: A. 
                and the value is accurate to one decimal place (.1).  
                If the value is 2147483647(0x7FFFFFFF), it indicates that the value is invalid."
            ::= { hwSSMGroupSampEntry 8 }

        hwSSMGroupTotalCapacity OBJECT-TYPE
            SYNTAX Unsigned32 (0..100000)
            MAX-ACCESS read-only
            STATUS current
            DESCRIPTION
                "The battery total capacity; Value range: 0.0 to 10000.0, 
                unit: Ah. 
                and the value is accurate to one decimal place (.1).   
                If the value is 2147483647(0x7FFFFFFF), it indicates that the value is invalid."
            ::= { hwSSMGroupSampEntry 9 }

        hwSSMGroupTotalRemainCapacity OBJECT-TYPE
            SYNTAX Unsigned32 (0..100)
            MAX-ACCESS read-only
            STATUS current
            DESCRIPTION
                "The battery total remain capacity; Value range:0 to 100, 
                unit: %. 
                and the value is an integer (1).  
                If the value is 2147483647(0x7FFFFFFF), it indicates that the value is invalid."
            ::= { hwSSMGroupSampEntry 10 }

        hwSSMGroupTemperature OBJECT-TYPE
            SYNTAX Integer32 (-50..100)
            MAX-ACCESS read-only
            STATUS current
            DESCRIPTION
                "The battery temperature; Value range:50 to 100, 
                unit: degC. 
                and the value is an integer (1).  
                If the value is 2147483647(0x7FFFFFFF), it indicates that the value is invalid."
            ::= { hwSSMGroupSampEntry 11 }

        hwSSMGroupTotalDisChargePower OBJECT-TYPE
            SYNTAX Unsigned32 (0..1000000000)
            MAX-ACCESS read-only
            STATUS current
            DESCRIPTION
                "The battery total dicharge power; Value range:0 to 1000000000, 
                unit: wh. 
                and the value is accurate to three decimal place (.001).   
                If the value is 2147483647(0x7FFFFFFF), it indicates that the value is invalid."
            ::= { hwSSMGroupSampEntry 12 }

        hwSSMGroupEsmuCommNum OBJECT-TYPE
            SYNTAX Unsigned32 (0..100)
            MAX-ACCESS read-only
            STATUS current
            DESCRIPTION
                "The esmu communicate number; 
                Value range: 0 to 100.   
                If the value is 2147483647(0x7FFFFFFF), it indicates that the value is invalid."
            ::= { hwSSMGroupSampEntry 13 }

        hwSSMGroupSetTable OBJECT-TYPE
            SYNTAX SEQUENCE OF HwSSMGroupSetEntry
            MAX-ACCESS not-accessible
             STATUS current
             DESCRIPTION
                ""
            ::= { hwSSMGroupEquip 2 }

        hwSSMGroupSetEntry OBJECT-TYPE
                        SYNTAX HwSSMGroupSetEntry
            MAX-ACCESS not-accessible
             STATUS current
             DESCRIPTION
                ""
            INDEX { hwSSMGroupHighTempThr }
            ::= { hwSSMGroupSetTable 1 }

        HwSSMGroupSetEntry            ::= SEQUENCE {
                hwSSMGroupHighTempThr
                    Unsigned32,
                hwSSMGroupLowTempThr
                    Integer32,
                hwSSMSohSubHealthVal
                    Unsigned32,
                hwSSMSohAgingVal
                    Unsigned32,
                hwSSMGroupClrFaultEquip
                    INTEGER
            }

        hwSSMGroupHighTempThr OBJECT-TYPE
            SYNTAX Unsigned32 (35..70)
            MAX-ACCESS read-write
            STATUS current
            DESCRIPTION
                "Upper threshold of the environment temperature alarm, can be configured by users. 
                Value range: 35 to 70, 
                unit: centigrade (°C), 
                and the value is an integer (1).  
                If the value is 2147483647(0x7FFFFFFF), it indicates that the value is invalid. "
            ::= { hwSSMGroupSetEntry 1 }

        hwSSMGroupLowTempThr OBJECT-TYPE
            SYNTAX Integer32 (-50..10)
            MAX-ACCESS read-write
            STATUS current
            DESCRIPTION
                "Lower threshold of the environment temperature alarm, can be configured by users. 
                Value range: -50 to 10, 
                unit: centigrade (degC), 
                and the value is an integer (1).  
                If the value is 2147483647(0x7FFFFFFF), it indicates that the value is invalid. "
            ::= { hwSSMGroupSetEntry 2 }

        hwSSMSohSubHealthVal OBJECT-TYPE
            SYNTAX Unsigned32 (0..100)
            MAX-ACCESS read-write
            STATUS current
            DESCRIPTION
                "Battert soh subhealthy value, can be configured by users. 
                Value range: 0 to 100, 
                unit:  (%), 
                and the value is an integer (1).  
                If the value is 2147483647(0x7FFFFFFF), it indicates that the value is invalid. 
                The default value is 80."
            ::= { hwSSMGroupSetEntry 3 }

        hwSSMSohAgingVal OBJECT-TYPE
            SYNTAX Unsigned32 (0..100)
            MAX-ACCESS read-write
            STATUS current
            DESCRIPTION
                "Battert soh ageing value, can be configured by users. 
                Value range: 0 to 100, 
                unit:  (%), 
                and the value is an integer (1).  
                If the value is 2147483647(0x7FFFFFFF), it indicates that the value is invalid. 
                The default value is 50."
            ::= { hwSSMGroupSetEntry 4 }

        hwSSMGroupClrFaultEquip OBJECT-TYPE
            SYNTAX INTEGER
                {
                yes(1),
                unknown(255)
                }
            MAX-ACCESS read-write
            STATUS current
            DESCRIPTION
                "Control clear up communicate fail equip. It is an enumeration value, and users actively set it. 
                If the enumeration value is 1, it means to enable clear up; "
            ::= { hwSSMGroupSetEntry 5 }

        hwSSMEquip OBJECT IDENTIFIER ::= { hwSiteSSM 2 }

        hwSSMBaseTable OBJECT-TYPE
            SYNTAX SEQUENCE OF HwSSMBaseEntry
            MAX-ACCESS not-accessible
             STATUS current
             DESCRIPTION
                ""
            ::= { hwSSMEquip 1 }

        hwSSMBaseEntry OBJECT-TYPE
                        SYNTAX HwSSMBaseEntry
            MAX-ACCESS not-accessible
             STATUS current
             DESCRIPTION
                ""
            INDEX { hwSSMIndex }
            ::= { hwSSMBaseTable 1 }

        HwSSMBaseEntry            ::= SEQUENCE {
                hwSSMIndex
                    Unsigned32,
                hwSSMEquipId
                    Unsigned32,
                hwSSMEquipName
                    OCTET STRING,
                hwSSMEquipAddr
                    Unsigned32,
                hwSSMSoftVar
                    OCTET STRING
            }

        hwSSMIndex OBJECT-TYPE
            SYNTAX Unsigned32
            MAX-ACCESS read-only
            STATUS current
            DESCRIPTION
                "SSM table index. Lines of the device list are restricted by the quantity of SSM."
            ::= { hwSSMBaseEntry 1 }

        hwSSMEquipId OBJECT-TYPE
            SYNTAX Unsigned32
            MAX-ACCESS read-only
            STATUS current
            DESCRIPTION
                "SSM device ID."
            ::= { hwSSMBaseEntry 2 }

        hwSSMEquipName OBJECT-TYPE
            SYNTAX OCTET STRING (SIZE (0..63))
            MAX-ACCESS read-only
            STATUS current
            DESCRIPTION
                "SSM equip name, of the character string type, is used to specify SSM.
                
                "
            ::= { hwSSMBaseEntry 3 }

        hwSSMEquipAddr OBJECT-TYPE
            SYNTAX Unsigned32 (0..255)
            MAX-ACCESS read-only
            STATUS current
            DESCRIPTION
                "The battery communica address."
            ::= { hwSSMBaseEntry 4 }

        hwSSMSoftVar OBJECT-TYPE
            SYNTAX OCTET STRING
            MAX-ACCESS read-only
            STATUS current
            DESCRIPTION
                "The Battery software version."
            ::= { hwSSMBaseEntry 5 }

        hwSSMSampTable OBJECT-TYPE
            SYNTAX SEQUENCE OF HwSSMSampEntry
            MAX-ACCESS not-accessible
             STATUS current
             DESCRIPTION
                ""
            ::= { hwSSMEquip 2 }

        hwSSMSampEntry OBJECT-TYPE
                        SYNTAX HwSSMSampEntry
            MAX-ACCESS not-accessible
             STATUS current
             DESCRIPTION
                ""
            INDEX { hwSSMBatVolt }
            ::= { hwSSMSampTable 1 }

        HwSSMSampEntry            ::= SEQUENCE {
                hwSSMBatVolt
                    Unsigned32,
                hwSSMBatCurr
                    Integer32,
                hwSSMRunningStatus
                    INTEGER,
                hwSSMBatSoh
                    Unsigned32,
                hwSSMBatCapacity
                    Unsigned32,
                hwSSMBatCell1Volt
                    Unsigned32,
                hwSSMBatCell2Volt
                    Unsigned32,
                hwSSMBatCell1Temp
                    Integer32,
                hwSSMBatCell2Temp
                    Integer32,
                hwSSMBatRemainCapacity
                    Unsigned32,
                hwSSMPVInputVoltage
                    Unsigned32,
                hwSSMPVInputCurrent
                    Integer32,
                hwSSMPVTotalOutputPower
                    Integer32,
                hwSSM12VOutputVoltage
                    Unsigned32,
                hwSSM12VOutputCurrent
                    Integer32,
                hwSSM12VOutputStatus
                    INTEGER
            }

        hwSSMBatVolt OBJECT-TYPE
            SYNTAX Unsigned32 (0..600)
            MAX-ACCESS read-only
            STATUS current
            DESCRIPTION
                "voltage of the battery. It indicates the real-time statistics of the battery on the site. 
                Value range: 0 to 60, 
                unit: V, 
                and the value is accurate to one decimal place (.1).  
                If the value is 2147483647(0x7FFFFFFF), it indicates that the value is invalid."
            ::= { hwSSMSampEntry 1 }

        hwSSMBatCurr OBJECT-TYPE
            SYNTAX Integer32 (-2000..2000)
            MAX-ACCESS read-only
            STATUS current
            DESCRIPTION
                "Current of the battery. It indicates the real-time statistics of the battery on the site. 
                Value range: -200 to 200, 
                unit: A, 
                and the value is accurate to one decimal place (.1).  
                If the value is 2147483647(0x7FFFFFFF), it indicates that the value is invalid."
            ::= { hwSSMSampEntry 2 }

        hwSSMRunningStatus OBJECT-TYPE
            SYNTAX INTEGER
                {
                offline(1),
                sleep(2),
                charge(3),
                discharge(4),
                standby(5),
                unknown(255)
                }
            MAX-ACCESS read-only
            STATUS current
            DESCRIPTION
                "Battery charging state, indicates the charging and discharging information about the battery group. It is an enumeration type. 
                If the enumeration value is 1, it indicates a battery is off line. 
                If the enumeration value is 2, it indicates a battery  is sleep. 
                If the enumeration value is 3, it indicates a battery  in the charge state.
                If the enumeration value is 4, it indicates a battery  in the discharge state.
                If the enumeration value is 5, it indicates a battery  in the standby state.
                If the enumeration value is 255, it indicates a battery group in the unknown state. "
            ::= { hwSSMSampEntry 3 }

        hwSSMBatSoh OBJECT-TYPE
            SYNTAX Unsigned32 (0..100)
            MAX-ACCESS read-only
            STATUS current
            DESCRIPTION
                "Soh of the battery. It indicates the real-time statistics of the battery on the site. 
                Value range: 0 to 100, 
                unit: %, 
                and the value is accurate to one decimal place (1).  
                If the value is 2147483647(0x7FFFFFFF), it indicates that the value is invalid."
            ::= { hwSSMSampEntry 4 }

        hwSSMBatCapacity OBJECT-TYPE
            SYNTAX Unsigned32 (0..100000)
            MAX-ACCESS read-only
            STATUS current
            DESCRIPTION
                "Capacity of the battery. It indicates the real-time statistics of the battery on the site. 
                Value range: 0 to 10000, 
                unit: Ah, 
                and the value is accurate to one decimal place (.1).  
                If the value is 2147483647(0x7FFFFFFF), it indicates that the value is invalid."
            ::= { hwSSMSampEntry 5 }

        hwSSMBatCell1Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).  
                If the value is 2147483647(0x7FFFFFFF), it indicates that the value is invalid."
            ::= { hwSSMSampEntry 6 }

        hwSSMBatCell2Volt OBJECT-TYPE
            SYNTAX Unsigned32 (0..500)
            MAX-ACCESS read-only
            STATUS current
            DESCRIPTION
                "Voltage of the battery cell. It indicates the real-time statistics of the battery on the site. 
                Value range: 0.00 to 5.00, 
                unit: V, 
                and the value is accurate to two decimal place (.01).  
                If the value is 2147483647(0x7FFFFFFF), it indicates that the value is invalid."
            ::= { hwSSMSampEntry 7 }

        hwSSMBatCell1Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal place (.1).  
                If the value is 2147483647(0x7FFFFFFF), it indicates that the value is invalid."
            ::= { hwSSMSampEntry 8 }

        hwSSMBatCell2Temp OBJECT-TYPE
            SYNTAX Integer32 (-500..1000)
            MAX-ACCESS read-only
            STATUS current
            DESCRIPTION
                "Temperature of the battery cell. It indicates the real-time statistics of the battery on the site. 
                Value range: -50.0 to 100.0, 
                unit: centigrade(degC), 
                and the value is accurate to one decimal place (.1).  
                If the value is 2147483647(0x7FFFFFFF), it indicates that the value is invalid."
            ::= { hwSSMSampEntry 9 }

        hwSSMBatRemainCapacity OBJECT-TYPE
            SYNTAX Unsigned32 (0..1000)
            MAX-ACCESS read-only
            STATUS current
            DESCRIPTION
                "The battery total remain capacity; Value range:0 to 100, 
                unit: %. 
                and the value is accurate to one decimal place (.1).   
                If the value is 2147483647(0x7FFFFFFF), it indicates that the value is invalid."
            ::= { hwSSMSampEntry 10 }

        hwSSMPVInputVoltage OBJECT-TYPE
            SYNTAX Unsigned32 (0..350)
            MAX-ACCESS read-only
            STATUS current
            DESCRIPTION
                "Input voltage of PV module."
            ::= { hwSSMSampEntry 11 }

        hwSSMPVInputCurrent OBJECT-TYPE
            SYNTAX Integer32 (-100..100)
            MAX-ACCESS read-only
            STATUS current
            DESCRIPTION
                "Input current of the PV module."
            ::= { hwSSMSampEntry 12 }

        hwSSMPVTotalOutputPower OBJECT-TYPE
            SYNTAX Integer32 (0..100000000)
            MAX-ACCESS read-only
            STATUS current
            DESCRIPTION
                "The PV output power; 
                Value range: 0 to 10000000.0, 
                and the value is accurate to two decimal place (.01), 
                If the value is 2147483647(0x7FFFFFFF), it indicates that the value is invalid."
            ::= { hwSSMSampEntry 13 }

        hwSSM12VOutputVoltage OBJECT-TYPE
            SYNTAX Unsigned32 (0..160)
            MAX-ACCESS read-only
            STATUS current
            DESCRIPTION
                "Output voltage of 12V port."
            ::= { hwSSMSampEntry 14 }

        hwSSM12VOutputCurrent OBJECT-TYPE
            SYNTAX Integer32 (-50..50)
            MAX-ACCESS read-only
            STATUS current
            DESCRIPTION
                "Output current of 12V port."
            ::= { hwSSMSampEntry 15 }

        hwSSM12VOutputStatus OBJECT-TYPE
            SYNTAX INTEGER
                {
                off(1),
                start(2),
                running(3),
                unknown(65535)
                }
            MAX-ACCESS read-only
            STATUS current
            DESCRIPTION
                "State of the 12V output state. It is an enumeration type: 
                  If the enumeration value is 0, it indicates that the 12V output is in the off state;
                  If the enumeration value is 1, it indicates that the 12V output is in the start state.
                  If the enumeration value is 2, it indicates that the 12V output is in the running state;
                  If the enumeration value is 0xffff, it indicates that the 12V output is in the unknown state."
            ::= { hwSSMSampEntry 16 }

        hwSSMSetTable OBJECT-TYPE
            SYNTAX SEQUENCE OF HwSSMSetEntry
            MAX-ACCESS not-accessible
             STATUS current
             DESCRIPTION
                ""
            ::= { hwSSMEquip 3 }

        hwSSMSetEntry OBJECT-TYPE
                        SYNTAX HwSSMSetEntry
            MAX-ACCESS not-accessible
             STATUS current
             DESCRIPTION
                ""
            INDEX { hwSSMReset }
            ::= { hwSSMSetTable 1 }

        HwSSMSetEntry            ::= SEQUENCE {
                hwSSMReset
                    INTEGER,
                hwSSMServiceStartDate
                    OCTET STRING,
                hwSSMServiceLife
                    Unsigned32
            }

        hwSSMReset OBJECT-TYPE
            SYNTAX INTEGER
                {
                yes(2),
                unknown(255)
                }
            MAX-ACCESS read-write
            STATUS current
            DESCRIPTION
                "Control reset equip. It is an enumeration value, and users actively set it. 
                If the enumeration value is 2, it means to enable reset; 
                If the enumeration value is 255, it indicates a battery group in the unknown state. "
            ::= { hwSSMSetEntry 1 }

        hwSSMServiceStartDate OBJECT-TYPE
            SYNTAX OCTET STRING (SIZE (0..127
))
            MAX-ACCESS read-write
            STATUS current
            DESCRIPTION
                "Service Start Time. String format YYYY-MM-DD."
            ::= { hwSSMSetEntry 2 }

        hwSSMServiceLife OBJECT-TYPE
            SYNTAX Unsigned32 (0..10
)
            MAX-ACCESS read-write
            STATUS current
            DESCRIPTION
                "Service Life"
            ::= { hwSSMSetEntry 3 }

        hwPoeEquip OBJECT IDENTIFIER ::= { hwSiteMonitorMIBObjects 52 }

        hwPoeBaseTable OBJECT-TYPE
            SYNTAX SEQUENCE OF HwPoeBaseEntry
            MAX-ACCESS not-accessible
             STATUS current
             DESCRIPTION
                ""
            ::= { hwPoeEquip 1 }

        hwPoeBaseEntry OBJECT-TYPE
                        SYNTAX HwPoeBaseEntry
            MAX-ACCESS not-accessible
             STATUS current
             DESCRIPTION
                ""
            INDEX { hwPoeIndex }
            ::= { hwPoeBaseTable 1 }

        HwPoeBaseEntry            ::= SEQUENCE {
                hwPoeIndex
                    Unsigned32,
                hwPoeEquipId
                    Unsigned32,
                hwPoeEquipName
                    OCTET STRING
            }

        hwPoeIndex OBJECT-TYPE
            SYNTAX Unsigned32
            MAX-ACCESS read-only
            STATUS current
            DESCRIPTION
                "Poe table index. Lines of the device list are restricted by the quantity of poe equip."
            ::= { hwPoeBaseEntry 1 }

        hwPoeEquipId OBJECT-TYPE
            SYNTAX Unsigned32
            MAX-ACCESS read-only
            STATUS current
            DESCRIPTION
                "Poe device ID."
            ::= { hwPoeBaseEntry 2 }

        hwPoeEquipName OBJECT-TYPE
            SYNTAX OCTET STRING (SIZE (0..63))
            MAX-ACCESS read-only
            STATUS current
            DESCRIPTION
                "Poe equip name, of the character string type, is used to specify poe.
                
                "
            ::= { hwPoeBaseEntry 3 }

        hwPoebSampTable OBJECT-TYPE
            SYNTAX SEQUENCE OF HwPoebSampEntry
            MAX-ACCESS not-accessible
             STATUS current
             DESCRIPTION
                ""
            ::= { hwPoeEquip 2 }

        hwPoebSampEntry OBJECT-TYPE
                        SYNTAX HwPoebSampEntry
            MAX-ACCESS not-accessible
             STATUS current
             DESCRIPTION
                ""
            INDEX { hwPoeCHOutputVoltage }
            ::= { hwPoebSampTable 1 }

        HwPoebSampEntry            ::= SEQUENCE {
                hwPoeCHOutputVoltage
                    Unsigned32,
                hwPoeCHOutputCurrent
                    Unsigned32,
                hwPoeCHOutputPower
                    Unsigned32
            }

        hwPoeCHOutputVoltage OBJECT-TYPE
            SYNTAX Unsigned32 (0..3000)
            MAX-ACCESS read-only
            STATUS current
            DESCRIPTION
                "POE channel 1 Output voltage, Value range: 0.0 to 300.0.Unit: V.and the value is accurate to one decimal space (.1).  If the value is 2147483647(0x7FFFFFFF), it indicates that the value is invalid."
            ::= { hwPoebSampEntry 1 }

        hwPoeCHOutputCurrent OBJECT-TYPE
            SYNTAX Unsigned32 (0..1000)
            MAX-ACCESS read-only
            STATUS current
            DESCRIPTION
                "POE channel 1 Output current, Value range: 0.0 to 100.0.Unit: A.and the value is accurate to one decimal space (.1).  If the value is 2147483647(0x7FFFFFFF), it indicates that the value is invalid."
            ::= { hwPoebSampEntry 2 }

        hwPoeCHOutputPower OBJECT-TYPE
            SYNTAX Unsigned32 (0..300000)
            MAX-ACCESS read-only
            STATUS current
            DESCRIPTION
                ""
            ::= { hwPoebSampEntry 3 }

        hwPoeSetTable OBJECT-TYPE
            SYNTAX SEQUENCE OF HwPoeSetEntry
            MAX-ACCESS not-accessible
             STATUS current
             DESCRIPTION
                ""
            ::= { hwPoeEquip 3 }

        hwPoeSetEntry OBJECT-TYPE
                        SYNTAX HwPoeSetEntry
            MAX-ACCESS not-accessible
             STATUS current
             DESCRIPTION
                ""
            INDEX { hwPoeCHCtrl }
            ::= { hwPoeSetTable 1 }

        HwPoeSetEntry            ::= SEQUENCE {
                hwPoeCHCtrl
                    INTEGER
            }

        hwPoeCHCtrl OBJECT-TYPE
            SYNTAX INTEGER
                {
                off(1),
                on(2),
                unknown(255)
                
                }
            MAX-ACCESS read-write
            STATUS current
            DESCRIPTION
                "control of the  POE channel
                  If the enumeration value is 0, it indicates that  the control channel is turned on; 
                  If the enumeration value is 1, it indicates that  the control fchannel is turned off;
                "
            ::= { hwPoeSetEntry 1 }

        hwSiteIDCDU OBJECT IDENTIFIER ::= { hwSiteMonitorMIBObjects 32 }

        hwIDCDUGroup OBJECT IDENTIFIER ::= { hwSiteIDCDU 1 }

        hwIDCDUGroupId OBJECT-TYPE
            SYNTAX Unsigned32
            MAX-ACCESS read-only
            STATUS current
            DESCRIPTION
                "Device group ID of the DCDB module. It is the unique ID of the rectifier module group, and its default value: 034,000. 
                  The first digits indicate the device type and the last three digits indicate the device SN. If the last three digits are 000, it indicates a virtual device. "
            ::= { hwIDCDUGroup 1 }

        hwIDCDUGroupName OBJECT-TYPE
            SYNTAX OCTET STRING (SIZE (0..63))
            MAX-ACCESS read-only
            STATUS current
            DESCRIPTION
                "Name of the DCDB module group, character string type, is used to specify the rectifier module group. Users can configure it. 
                  Otherwise, the configured character can not be any other languages except English."
            ::= { hwIDCDUGroup 2 }

        hwIDCDUTotalQuantity OBJECT-TYPE
            SYNTAX Unsigned32 (0..65535)
            MAX-ACCESS read-only
            STATUS current
            DESCRIPTION
                "Total quantity of the DCDB modules. Value range: 0 to 65535. unit:pcs."
            ::= { hwIDCDUGroup 3 }

        hwIDCDU OBJECT IDENTIFIER ::= { hwSiteIDCDU 2 }

        hwIDCDUSampTable OBJECT-TYPE
            SYNTAX SEQUENCE OF HwIDCDUSampEntry
            MAX-ACCESS not-accessible
             STATUS current
             DESCRIPTION
                "/"
            ::= { hwIDCDU 1 }

        hwIDCDUSampEntry OBJECT-TYPE
                        SYNTAX HwIDCDUSampEntry
            MAX-ACCESS not-accessible
             STATUS current
             DESCRIPTION
                "/"
            INDEX { hwIDCDUSampIndex }
            ::= { hwIDCDUSampTable 1 }

        HwIDCDUSampEntry            ::= SEQUENCE {
                hwIDCDUSampIndex
                    Integer32,
                hwIDCDUEquipId
                    Unsigned32,
                hwIDCDUEquipName
                    OCTET STRING,
                hwIDCDUOutputVoltage
                    Unsigned32,
                hwIDCDULoadNumber
                    Unsigned32,
                hwIDCDUTotalOutputCurrent
                    Unsigned32,
                hwIDCDULoad1Current
                    Unsigned32,
                hwIDCDULoad2Current
                    Unsigned32,
                hwIDCDULoad3Current
                    Unsigned32,
                hwIDCDULoad4Current
                    Unsigned32,
                hwIDCDUTotalOutputPower
                    Unsigned32,
                hwIDCDULoad1Power
                    Unsigned32,
                hwIDCDULoad2Power
                    Unsigned32,
                hwIDCDULoad3Power
                    Unsigned32,
                hwIDCDULoad4Power
                    Unsigned32,
                hwIDCDUTotalOutputConsum
                    Unsigned32,
                hwIDCDULoad1Consum
                    Unsigned32,
                hwIDCDULoad2Consum
                    Unsigned32,
                hwIDCDULoad3Consum
                    Unsigned32,
                hwIDCDULoad4Consum
                    Unsigned32
            }

        hwIDCDUSampIndex OBJECT-TYPE
            SYNTAX Integer32 (1..256)
            MAX-ACCESS read-only
            STATUS current
            DESCRIPTION
                "Table index of the running IDCDU modules, which value range: 1 to 256(To the actual subject). Lines of the device list are restricted by the total quantity of the IDCDU modules (hwDCDBTotalQuantity)."
            ::= { hwIDCDUSampEntry 1 }

        hwIDCDUEquipId OBJECT-TYPE
            SYNTAX Unsigned32 (1..255)
            MAX-ACCESS read-only
            STATUS current
            DESCRIPTION
                "IDCDU module ID. Value range: 002'001 to 002'255. The first digits indicate the device type and last three digits indicate the device SN."
            ::= { hwIDCDUSampEntry 2 }

        hwIDCDUEquipName OBJECT-TYPE
            SYNTAX OCTET STRING (SIZE (0..63))
            MAX-ACCESS read-only
            STATUS current
            DESCRIPTION
                "Device name of the IDCDU module, character string type, is used to specify the IDCDU module. Users can configure it. 
                  Otherwise, the configured character can not be any other languages except English."
            ::= { hwIDCDUSampEntry 3 }

        hwIDCDUOutputVoltage OBJECT-TYPE
            SYNTAX Unsigned32 (0..1000)
            MAX-ACCESS read-only
            STATUS current
            DESCRIPTION
                "Output voltage of the IDCDU module. It is a real-time analog parameter. Value range: 0 to 100.0, unit: V, the value is accurate to one decimal place (.1). If the value is 2147483647(0x7FFFFFFF), it indicates that the value is invalid. "
            ::= { hwIDCDUSampEntry 4 }

        hwIDCDULoadNumber OBJECT-TYPE
            SYNTAX Unsigned32 (0..65535)
            MAX-ACCESS read-only
            STATUS current
            DESCRIPTION
                "Total load number. Value range: 0 to 65535, unit: NA, and the value is an integer. If the value is 2147483647(0x7FFFFFFF), it indicates that the value is invalid."
            ::= { hwIDCDUSampEntry 5 }

        hwIDCDUTotalOutputCurrent OBJECT-TYPE
            SYNTAX Unsigned32 (0..300000)
            MAX-ACCESS read-only
            STATUS current
            DESCRIPTION
                "Total output current of the IDCDU module. It is a real-time analog parameter. Value range: 0.0 to 30000.0, unit: A, and the value is accurate to one decimal place (.1).  If the value is 2147483647(0x7FFFFFFF), it indicates that the value is invalid."
            ::= { hwIDCDUSampEntry 6 }

        hwIDCDULoad1Current OBJECT-TYPE
            SYNTAX Unsigned32 (0..300000)
            MAX-ACCESS read-only
            STATUS current
            DESCRIPTION
                "Load 1 output current of the IDCDU module. It is a real-time analog parameter. Value range: 0 to 30000.0, unit: A, and the value is accurate to one decimal place (.1).  If the value is 2147483647(0x7FFFFFFF), it indicates that the value is invalid."
            ::= { hwIDCDUSampEntry 7 }

        hwIDCDULoad2Current OBJECT-TYPE
            SYNTAX Unsigned32 (0..300000)
            MAX-ACCESS read-only
            STATUS current
            DESCRIPTION
                "Load 2 output current of the IDCDU module. It is a real-time analog parameter. Value range: 0 to 30000.0, unit: A, and the value is accurate to one decimal place (.1).  If the value is 2147483647(0x7FFFFFFF), it indicates that the value is invalid."
            ::= { hwIDCDUSampEntry 8 }

        hwIDCDULoad3Current OBJECT-TYPE
            SYNTAX Unsigned32 (0..300000)
            MAX-ACCESS read-only
            STATUS current
            DESCRIPTION
                "Load 3 output current of the IDCDU module. It is a real-time analog parameter. Value range: 0 to 30000.0, unit: A, and the value is accurate to one decimal place (.1).  If the value is 2147483647(0x7FFFFFFF), it indicates that the value is invalid."
            ::= { hwIDCDUSampEntry 9 }

        hwIDCDULoad4Current OBJECT-TYPE
            SYNTAX Unsigned32 (0..300000)
            MAX-ACCESS read-only
            STATUS current
            DESCRIPTION
                "Load 4 output current of the IDCDU module. It is a real-time analog parameter. Value range: 0 to 30000.0, unit: A, and the value is accurate to one decimal place (.1).  If the value is 2147483647(0x7FFFFFFF), it indicates that the value is invalid."
            ::= { hwIDCDUSampEntry 10 }

        hwIDCDUTotalOutputPower OBJECT-TYPE
            SYNTAX Unsigned32 (0..300000)
            MAX-ACCESS read-only
            STATUS current
            DESCRIPTION
                "Total output power. Value range: 0.00 to 3000.00, unit: kW, and the value is an integer. If the value is 2147483647(0x7FFFFFFF), it indicates that the value is invalid."
            ::= { hwIDCDUSampEntry 11 }

        hwIDCDULoad1Power OBJECT-TYPE
            SYNTAX Unsigned32 (0..300000)
            MAX-ACCESS read-only
            STATUS current
            DESCRIPTION
                "Load 1 output power. Value range: 0.00 to 3000.00, unit: kW, and the value is an integer. If the value is 2147483647(0x7FFFFFFF), it indicates that the value is invalid."
            ::= { hwIDCDUSampEntry 12 }

        hwIDCDULoad2Power OBJECT-TYPE
            SYNTAX Unsigned32 (0..300000)
            MAX-ACCESS read-only
            STATUS current
            DESCRIPTION
                "Load 2 output power. Value range: 0.00 to 3000.00, unit: kW, and the value is an integer. If the value is 2147483647(0x7FFFFFFF), it indicates that the value is invalid."
            ::= { hwIDCDUSampEntry 13 }

        hwIDCDULoad3Power OBJECT-TYPE
            SYNTAX Unsigned32 (0..300000)
            MAX-ACCESS read-only
            STATUS current
            DESCRIPTION
                "Load 3 output power. Value range: 0.00 to 3000.00, unit: kW, and the value is an integer. If the value is 2147483647(0x7FFFFFFF), it indicates that the value is invalid."
            ::= { hwIDCDUSampEntry 14 }

        hwIDCDULoad4Power OBJECT-TYPE
            SYNTAX Unsigned32 (0..300000)
            MAX-ACCESS read-only
            STATUS current
            DESCRIPTION
                "Load 4 output power. Value range: 0.00 to 3000.00, unit: kW, and the value is an integer. If the value is 2147483647(0x7FFFFFFF), it indicates that the value is invalid."
            ::= { hwIDCDUSampEntry 15 }

        hwIDCDUTotalOutputConsum OBJECT-TYPE
            SYNTAX Unsigned32 (0..4294967295)
            MAX-ACCESS read-only
            STATUS current
            DESCRIPTION
                "Total output consum. Value range: 0 to 429496729, unit: kWh, and the value is two decimal space (.01). If the value is 2147483647(0x7FFFFFFF), it indicates that the value is invalid."
            ::= { hwIDCDUSampEntry 16 }

        hwIDCDULoad1Consum OBJECT-TYPE
            SYNTAX Unsigned32 (0..4294967295)
            MAX-ACCESS read-only
            STATUS current
            DESCRIPTION
                "Load 1 output consum. Value range: 0 to 429496729, unit: kWh, and the value is two decimal space (.01). If the value is 2147483647(0x7FFFFFFF), it indicates that the value is invalid."
            ::= { hwIDCDUSampEntry 17 }

        hwIDCDULoad2Consum OBJECT-TYPE
            SYNTAX Unsigned32 (0..4294967295)
            MAX-ACCESS read-only
            STATUS current
            DESCRIPTION
                "Load 2 output consum. Value range: 0 to 429496729, unit: kWh, and the value is two decimal space (.01). If the value is 2147483647(0x7FFFFFFF), it indicates that the value is invalid."
            ::= { hwIDCDUSampEntry 18 }

        hwIDCDULoad3Consum OBJECT-TYPE
            SYNTAX Unsigned32 (0..4294967295)
            MAX-ACCESS read-only
            STATUS current
            DESCRIPTION
                "Load 3 output consum. Value range: 0 to 429496729, unit: kWh, and the value is two decimal space (.01). If the value is 2147483647(0x7FFFFFFF), it indicates that the value is invalid."
            ::= { hwIDCDUSampEntry 19 }

        hwIDCDULoad4Consum OBJECT-TYPE
            SYNTAX Unsigned32 (0..4294967295)
            MAX-ACCESS read-only
            STATUS current
            DESCRIPTION
                "Load 4 output consum. Value range: 0 to 429496729, unit: kWh, and the value is two decimal space (.01). If the value is 2147483647(0x7FFFFFFF), it indicates that the value is invalid."
            ::= { hwIDCDUSampEntry 20 }

        hwSiteIDCDUSetTable OBJECT-TYPE
            SYNTAX SEQUENCE OF HwSiteIDCDUSetEntry
            MAX-ACCESS not-accessible
             STATUS current
             DESCRIPTION
                "/"
            ::= { hwIDCDU 2 }

        hwSiteIDCDUSetEntry OBJECT-TYPE
                        SYNTAX HwSiteIDCDUSetEntry
            MAX-ACCESS not-accessible
             STATUS current
             DESCRIPTION
                "/"
            INDEX { hwIDCDULoadSettingMode }
            ::= { hwSiteIDCDUSetTable 1 }

        HwSiteIDCDUSetEntry            ::= SEQUENCE {
                hwIDCDULoadSettingMode
                    INTEGER,
                hwIDCDULvdMode
                    INTEGER,
                hwIDCDUTotalLoadLvdEnable
                    INTEGER,
                hwIDCDULoad1LvdEnable
                    INTEGER,
                hwIDCDULoad2LvdEnable
                    INTEGER,
                hwIDCDULoad3LvdEnable
                    INTEGER,
                hwIDCDULoad4LvdEnable
                    INTEGER,
                hwIDCDUTotalLvdVoltage
                    Unsigned32,
                hwIDCDULoad1LvdVoltage
                    Integer32,
                hwIDCDULoad2LvdVoltage
                    Integer32,
                hwIDCDULoad3LvdVoltage
                    Integer32,
                hwIDCDULoad4LvdVoltage
                    Integer32,
                hwIDCDUTotalLvdReconVoltage
                    Unsigned32,
                hwIDCDULoad1LvdReconVoltage
                    Unsigned32,
                hwIDCDULoad2LvdReconVoltage
                    Unsigned32,
                hwIDCDULoad3LvdReconVoltage
                    Unsigned32,
                hwIDCDULoad4LvdReconVoltage
                    Unsigned32,
                hwIDCDUTotalLvdTime
                    Integer32,
                hwIDCDULoad1LvdTime
                    Integer32,
                hwIDCDULoad2LvdTime
                    Integer32,
                hwIDCDULoad3LvdTime
                    Integer32,
                hwIDCDULoad4LvdTime
                    Integer32,
                hwIDCDUTotalLvdCapacity
                    Unsigned32,
                hwIDCDULoad1LvdCapacity
                    Unsigned32,
                hwIDCDULoad2LvdCapacity
                    Unsigned32,
                hwIDCDULoad3LvdCapacity
                    Unsigned32,
                hwIDCDULoad4LvdCapacity
                    Unsigned32,
                hwIDCDUTotalLvdPDEnable
                    INTEGER,
                hwIDCDULoad1LvdPDEnable
                    INTEGER,
                hwIDCDULoad2LvdPDEnable
                    INTEGER,
                hwIDCDULoad3LvdPDEnable
                    INTEGER,
                hwIDCDULoad4LvdPDEnable
                    INTEGER,
                hwIDCDUTotalLvdPDTime
                    OCTET STRING,
                hwIDCDULoad1LvdPDTime
                    OCTET STRING,
                hwIDCDULoad2LvdPDTime
                    OCTET STRING,
                hwIDCDULoad3LvdPDTime
                    OCTET STRING,
                hwIDCDULoad4LvdPDTime
                    OCTET STRING,
                hwIDCDUTotalLvdPDDuration
                    Integer32,
                hwIDCDULoad1LvdPDDuration
                    Integer32,
                hwIDCDULoad2LvdPDDuration
                    Integer32,
                hwIDCDULoad3LvdPDDuration
                    Integer32,
                hwIDCDULoad4LvdPDDuration
                    Integer32,
                hwIDCDULoadTotalDGOff
                    INTEGER,
                hwIDCDULoad1DGOff
                    INTEGER,
                hwIDCDULoad2DGOff
                    INTEGER,
                hwIDCDULoad3DGOff
                    INTEGER,
                hwIDCDULoad4DGOff
                    INTEGER,
                hwIDCDULoad1LvdMode
                    INTEGER,
                hwIDCDULoad2LvdMode
                    INTEGER,
                hwIDCDULoad3LvdMode
                    INTEGER,
                hwIDCDULoad4LvdMode
                    INTEGER,
                hwIDCDUTotalLoadOverCurrent
                    Unsigned32,
                hwIDCDULoad1OverCurrent
                    Unsigned32,
                hwIDCDULoad2OverCurrent
                    Unsigned32,
                hwIDCDULoad3OverCurrent
                    Unsigned32,
                hwIDCDULoad4OverCurrent
                    Unsigned32,
                hwIDCDUTotalLoadOffConsum
                    Unsigned32,
                hwIDCDULoad1OffConsum
                    Unsigned32,
                hwIDCDULoad2OffConsum
                    Unsigned32,
                hwIDCDULoad3OffConsum
                    Unsigned32,
                hwIDCDULoad4OffConsum
                    Unsigned32,
                hwIDCDULoadUserCfg
                    INTEGER,
                hwIDCDULoad1UserCfg
                    INTEGER,
                hwIDCDULoad2UserCfg
                    INTEGER,
                hwIDCDULoad3UserCfg
                    INTEGER,
                hwIDCDULoad4UserCfg
                    INTEGER,
                hwIDCDULoad1BranchCfg
                    INTEGER,
                hwIDCDULoad2BranchCfg
                    INTEGER,
                hwIDCDULoad3BranchCfg
                    INTEGER,
                hwIDCDULoad4BranchCfg
                    INTEGER,
                hwIDCDULoadPDStartTime2
                    OCTET STRING,
                hwIDCDULoad1PDStartTime2
                    OCTET STRING,
                hwIDCDULoad2PDStartTime2
                    OCTET STRING,
                hwIDCDULoad3PDStartTime2
                    OCTET STRING,
                hwIDCDULoad4PDStartTime2
                    OCTET STRING,
                hwIDCDULoadPDDuration2
                    Unsigned32,
                hwIDCDULoad1PDDuration2
                    Unsigned32,
                hwIDCDULoad2PDDuration2
                    Unsigned32,
                hwIDCDULoad3PDDuration2
                    Unsigned32,
                hwIDCDULoad4PDDuration2
                    Unsigned32,
                hwIDCDULoadPDStartTime3
                    OCTET STRING,
                hwIDCDULoad1PDStartTime3
                    OCTET STRING,
                hwIDCDULoad2PDStartTime3
                    OCTET STRING,
                hwIDCDULoad3PDStartTime3
                    OCTET STRING,
                hwIDCDULoad4PDStartTime3
                    OCTET STRING,
                hwIDCDULoadPDDuration3
                    Unsigned32,
                hwIDCDULoad1PDDuration3
                    Unsigned32,
                hwIDCDULoad2PDDuration3
                    Unsigned32,
                hwIDCDULoad3PDDuration3
                    Unsigned32,
                hwIDCDULoad4PDDuration3
                    Unsigned32,
                hwIDCDULoadPDStartTime4
                    OCTET STRING,
                hwIDCDULoad1PDStartTime4
                    OCTET STRING,
                hwIDCDULoad2PDStartTime4
                    OCTET STRING,
                hwIDCDULoad3PDStartTime4
                    OCTET STRING,
                hwIDCDULoad4PDStartTime4
                    OCTET STRING,
                hwIDCDULoadPDDuration4
                    Unsigned32,
                hwIDCDULoad1PDDuration4
                    Unsigned32,
                hwIDCDULoad2PDDuration4
                    Unsigned32,
                hwIDCDULoad3PDDuration4
                    Unsigned32,
                hwIDCDULoad4PDDuration4
                    Unsigned32,
                hwIDCDULoadPDStartTime5
                    OCTET STRING,
                hwIDCDULoad1PDStartTime5
                    OCTET STRING,
                hwIDCDULoad2PDStartTime5
                    OCTET STRING,
                hwIDCDULoad3PDStartTime5
                    OCTET STRING,
                hwIDCDULoad4PDStartTime5
                    OCTET STRING,
                hwIDCDULoadPDDuration5
                    Unsigned32,
                hwIDCDULoad1PDDuration5
                    Unsigned32,
                hwIDCDULoad2PDDuration5
                    Unsigned32,
                hwIDCDULoad3PDDuration5
                    Unsigned32,
                hwIDCDULoad4PDDuration5
                    Unsigned32,
                hwIDCDUExemptPeriodNoBK
                    INTEGER,
                hwIDCDUExemptPeriodNoBK1
                    INTEGER,
                hwIDCDUExemptPeriodNoBK2
                    INTEGER,
                hwIDCDUExemptPeriodNoBK3
                    INTEGER,
                hwIDCDUExemptPeriodNoBK4
                    INTEGER,
                hwIDCDULoadExemptPeriodStartTime1
                    OCTET STRING,
                hwIDCDULoad1ExemptPeriodStartTime1
                    OCTET STRING,
                hwIDCDULoad2ExemptPeriodStartTime1
                    OCTET STRING,
                hwIDCDULoad3ExemptPeriodStartTime1
                    OCTET STRING,
                hwIDCDULoad4ExemptPeriodStartTime1
                    OCTET STRING,
                hwIDCDULoadExemptPeriodDuration1
                    Unsigned32,
                hwIDCDULoad1ExemptPeriodDuration1
                    Unsigned32,
                hwIDCDULoad2ExemptPeriodDuration1
                    Unsigned32,
                hwIDCDULoad3ExemptPeriodDuration1
                    Unsigned32,
                hwIDCDULoad4ExemptPeriodDuration1
                    Unsigned32,
                hwIDCDULoadExemptPeriodStartTime2
                    OCTET STRING,
                hwIDCDULoad1ExemptPeriodStartTime2
                    OCTET STRING,
                hwIDCDULoad2ExemptPeriodStartTime2
                    OCTET STRING,
                hwIDCDULoad3ExemptPeriodStartTime2
                    OCTET STRING,
                hwIDCDULoad4ExemptPeriodStartTime2
                    OCTET STRING,
                hwIDCDULoadExemptPeriodDuration2
                    Unsigned32,
                hwIDCDULoad1ExemptPeriodDuration2
                    Unsigned32,
                hwIDCDULoad2ExemptPeriodDuration2
                    Unsigned32,
                hwIDCDULoad3ExemptPeriodDuration2
                    Unsigned32,
                hwIDCDULoad4ExemptPeriodDuration2
                    Unsigned32,
                hwIDCDULoadExemptPeriodStartTime3
                    OCTET STRING,
                hwIDCDULoad1ExemptPeriodStartTime3
                    OCTET STRING,
                hwIDCDULoad2ExemptPeriodStartTime3
                    OCTET STRING,
                hwIDCDULoad3ExemptPeriodStartTime3
                    OCTET STRING,
                hwIDCDULoad4ExemptPeriodStartTime3
                    OCTET STRING,
                hwIDCDULoadExemptPeriodDuration3
                    Unsigned32,
                hwIDCDULoad1ExemptPeriodDuration3
                    Unsigned32,
                hwIDCDULoad2ExemptPeriodDuration3
                    Unsigned32,
                hwIDCDULoad3ExemptPeriodDuration3
                    Unsigned32,
                hwIDCDULoad4ExemptPeriodDuration3
                    Unsigned32,
                hwIDCDULoadExemptPeriodStartTime4
                    OCTET STRING,
                hwIDCDULoad1ExemptPeriodStartTime4
                    OCTET STRING,
                hwIDCDULoad2ExemptPeriodStartTime4
                    OCTET STRING,
                hwIDCDULoad3ExemptPeriodStartTime4
                    OCTET STRING,
                hwIDCDULoad4ExemptPeriodStartTime4
                    OCTET STRING,
                hwIDCDULoadExemptPeriodDuration4
                    Unsigned32,
                hwIDCDULoad1ExemptPeriodDuration4
                    Unsigned32,
                hwIDCDULoad2ExemptPeriodDuration4
                    Unsigned32,
                hwIDCDULoad3ExemptPeriodDuration4
                    Unsigned32,
                hwIDCDULoad4ExemptPeriodDuration4
                    Unsigned32,
                hwIDCDULoadExemptPeriodStartTime5
                    OCTET STRING,
                hwIDCDULoad1ExemptPeriodStartTime5
                    OCTET STRING,
                hwIDCDULoad2ExemptPeriodStartTime5
                    OCTET STRING,
                hwIDCDULoad3ExemptPeriodStartTime5
                    OCTET STRING,
                hwIDCDULoad4ExemptPeriodStartTime5
                    OCTET STRING,
                hwIDCDULoadExemptPeriodDuration5
                    Unsigned32,
                hwIDCDULoad1ExemptPeriodDuration5
                    Unsigned32,
                hwIDCDULoad2ExemptPeriodDuration5
                    Unsigned32,
                hwIDCDULoad3ExemptPeriodDuration5
                    Unsigned32,
                hwIDCDULoad4ExemptPeriodDuration5
                    Unsigned32,
                hwIDCDULoadPeakShavingEnable
                    INTEGER,
                hwIDCDULoad1PeakShavingEnable
                    INTEGER,
                hwIDCDULoad2PeakShavingEnable
                    INTEGER,
                hwIDCDULoad3PeakShavingEnable
                    INTEGER,
                hwIDCDULoad4PeakShavingEnable
                    INTEGER
            }

        hwIDCDULoadSettingMode OBJECT-TYPE
            SYNTAX INTEGER
                {
                allBranch(1),
                singleBranch(2),
                unknown(255)
                }
            MAX-ACCESS read-write
            STATUS current
            DESCRIPTION
                "Specific type of the IDCDU module load setting mode. It is an enumeration type:
                If the enumeration value is 1, it indicates that all branchs are setted totally; 
                If the enumeration value is 2, it indicates that every branch is setted seperately."
            ::= { hwSiteIDCDUSetEntry 1 }

        hwIDCDULvdMode OBJECT-TYPE
            SYNTAX INTEGER
                {
                voltageMode(1),
                timeMode(2),
                capacityMode(3),
                consumptionMode(4),
                unknown(255)
                }
            MAX-ACCESS read-write
            STATUS current
            DESCRIPTION
                "Specific type of the IDCDU module lvd mode. It is an enumeration type:
                If the enumeration value is 1, it indicates voltage mode; 
                If the enumeration value is 2, it indicates time mode.
                If the enumeration value is 3, it indicates capacity mode.
                If the enumeration value is 4, it indicates consumption mode.
                If the enumeration value is 255, it indicates unknown mode."
            ::= { hwSiteIDCDUSetEntry 2 }

        hwIDCDUTotalLoadLvdEnable OBJECT-TYPE
            SYNTAX INTEGER
                {
                no(1),
                yes(2),
                unknown(255)
                }
            MAX-ACCESS read-write
            STATUS current
            DESCRIPTION
                "Specific type of the IDCDU module total load lvd enable or not. It is an enumeration type:
                If the enumeration value is 1, it indicates that lvd is enabled; 
                If the enumeration value is 2, it indicates that lvd is disenabled."
            ::= { hwSiteIDCDUSetEntry 3 }

        hwIDCDULoad1LvdEnable OBJECT-TYPE
            SYNTAX INTEGER
                {
                no(1),
                yes(2),
                unknown(255)
                }
            MAX-ACCESS read-write
            STATUS current
            DESCRIPTION
                "Specific type of the IDCDU module load 1 lvd enable or not. It is an enumeration type:
                If the enumeration value is 1, it indicates that lvd is enabled; 
                If the enumeration value is 2, it indicates that lvd is disenabled."
            ::= { hwSiteIDCDUSetEntry 4 }

        hwIDCDULoad2LvdEnable OBJECT-TYPE
            SYNTAX INTEGER
                {
                no(1),
                yes(2),
                unknown(255)
                }
            MAX-ACCESS read-write
            STATUS current
            DESCRIPTION
                "Specific type of the IDCDU module load 2 lvd enable or not. It is an enumeration type:
                If the enumeration value is 1, it indicates that lvd is enabled; 
                If the enumeration value is 2, it indicates that lvd is disenabled."
            ::= { hwSiteIDCDUSetEntry 5 }

        hwIDCDULoad3LvdEnable OBJECT-TYPE
            SYNTAX INTEGER
                {
                no(1),
                yes(2),
                unknown(255)
                }
            MAX-ACCESS read-write
            STATUS current
            DESCRIPTION
                "Specific type of the IDCDU module load 3 lvd enable or not. It is an enumeration type:
                If the enumeration value is 1, it indicates that lvd is enabled; 
                If the enumeration value is 2, it indicates that lvd is disenabled."
            ::= { hwSiteIDCDUSetEntry 6 }

        hwIDCDULoad4LvdEnable OBJECT-TYPE
            SYNTAX INTEGER
                {
                no(1),
                yes(2),
                unknown(255)
                }
            MAX-ACCESS read-write
            STATUS current
            DESCRIPTION
                "Specific type of the IDCDU module load 4 lvd enable or not. It is an enumeration type:
                If the enumeration value is 1, it indicates that lvd is enabled; 
                If the enumeration value is 2, it indicates that lvd is disenabled."
            ::= { hwSiteIDCDUSetEntry 7 }

        hwIDCDUTotalLvdVoltage OBJECT-TYPE
            SYNTAX Unsigned32 (360..560)
            MAX-ACCESS read-write
            STATUS current
            DESCRIPTION
                "Low-voltage power-off voltage of the IDCDU unit can be configured by users. 
                Its value range: 360 to 560, 
                unit: V, 
                and the value is accurate to one decimal space (.1).  
                If the value is 2147483647(0x7FFFFFFF), it indicates that the value is invalid."
            ::= { hwSiteIDCDUSetEntry 8 }

        hwIDCDULoad1LvdVoltage OBJECT-TYPE
            SYNTAX Integer32 (360..560)
            MAX-ACCESS read-write
            STATUS current
            DESCRIPTION
                "Low-voltage power-off voltage of the IDCDU load1 unit can be configured by users. 
                Its value range: 36 to 56, 
                unit: V, 
                and the value is accurate to one decimal space (.1).  
                If the value is 2147483647(0x7FFFFFFF), it indicates that the value is invalid."
            ::= { hwSiteIDCDUSetEntry 9 }

        hwIDCDULoad2LvdVoltage OBJECT-TYPE
            SYNTAX Integer32 (360..560)
            MAX-ACCESS read-write
            STATUS current
            DESCRIPTION
                "ow-voltage power-off voltage of the IDCDU load2 unit can be configured by users. 
                Its value range: 360 to 560, 
                unit: V, 
                and the value is accurate to one decimal space (.1).  
                If the value is 2147483647(0x7FFFFFFF), it indicates that the value is invalid."
            ::= { hwSiteIDCDUSetEntry 10 }

        hwIDCDULoad3LvdVoltage OBJECT-TYPE
            SYNTAX Integer32 (360..560)
            MAX-ACCESS read-write
            STATUS current
            DESCRIPTION
                "ow-voltage power-off voltage of the IDCDU load3 unit can be configured by users. 
                Its value range: 360 to 560, 
                unit: V, 
                and the value is accurate to one decimal space (.1).  
                If the value is 2147483647(0x7FFFFFFF), it indicates that the value is invalid."
            ::= { hwSiteIDCDUSetEntry 11 }

        hwIDCDULoad4LvdVoltage OBJECT-TYPE
            SYNTAX Integer32 (360..560)
            MAX-ACCESS read-write
            STATUS current
            DESCRIPTION
                "ow-voltage power-off voltage of the IDCDU load4 unit can be configured by users. 
                Its value range: 360 to 560, 
                unit: V, 
                and the value is accurate to one decimal space (.1).  
                If the value is 2147483647(0x7FFFFFFF), it indicates that the value is invalid."
            ::= { hwSiteIDCDUSetEntry 12 }

        hwIDCDUTotalLvdReconVoltage OBJECT-TYPE
            SYNTAX Unsigned32 (370..580)
            MAX-ACCESS read-write
            STATUS current
            DESCRIPTION
                "Low-voltage power-off recover of the IDCDU unit can be configured by users. Its value range: 370 to 580, unit: V, and the value is accurate to one decimal space (.1).  If the value is 2147483647(0x7FFFFFFF), it indicates that the value is invalid.
                NOTE: There is linkage between hwIDCDUTotalLvdVoltage and hwIDCDUTotalLvdReconVoltage"
            ::= { hwSiteIDCDUSetEntry 13 }

        hwIDCDULoad1LvdReconVoltage OBJECT-TYPE
            SYNTAX Unsigned32 (370..580)
            MAX-ACCESS read-write
            STATUS current
            DESCRIPTION
                "Low-voltage power-off recover of the IDCDU load1 unit can be configured by users. Its value range: 370 to 580, unit: V, and the value is accurate to one decimal space (.1).  If the value is 2147483647(0x7FFFFFFF), it indicates that the value is invalid.
                NOTE: There is linkage between hwIDCDUTotalLvdVoltage and hwIDCDUTotalLvdReconVoltage"
            ::= { hwSiteIDCDUSetEntry 14 }

        hwIDCDULoad2LvdReconVoltage OBJECT-TYPE
            SYNTAX Unsigned32 (370..580)
            MAX-ACCESS read-write
            STATUS current
            DESCRIPTION
                "Low-voltage power-off recover of the IDCDU load2 unit can be configured by users. Its value range: 370 to 580, unit: V, and the value is accurate to one decimal space (.1).  If the value is 2147483647(0x7FFFFFFF), it indicates that the value is invalid.
                NOTE: There is linkage between hwIDCDUTotalLvdVoltage and hwIDCDUTotalLvdReconVoltage"
            ::= { hwSiteIDCDUSetEntry 15 }

        hwIDCDULoad3LvdReconVoltage OBJECT-TYPE
            SYNTAX Unsigned32 (370..580)
            MAX-ACCESS read-write
            STATUS current
            DESCRIPTION
                "Low-voltage power-off recover of the IDCDU load3 unit can be configured by users. Its value range: 370 to 580, unit: V, and the value is accurate to one decimal space (.1).  If the value is 2147483647(0x7FFFFFFF), it indicates that the value is invalid.
                NOTE: There is linkage between hwIDCDUTotalLvdVoltage and hwIDCDUTotalLvdReconVoltage"
            ::= { hwSiteIDCDUSetEntry 16 }

        hwIDCDULoad4LvdReconVoltage OBJECT-TYPE
            SYNTAX Unsigned32 (370..580)
            MAX-ACCESS read-write
            STATUS current
            DESCRIPTION
                "Low-voltage power-off recover of the IDCDU load4 unit can be configured by users. Its value range: 370 to 580, unit: V, and the value is accurate to one decimal space (.1).  If the value is 2147483647(0x7FFFFFFF), it indicates that the value is invalid.
                NOTE: There is linkage between hwIDCDUTotalLvdVoltage and hwIDCDUTotalLvdReconVoltage"
            ::= { hwSiteIDCDUSetEntry 17 }

        hwIDCDUTotalLvdTime OBJECT-TYPE
            SYNTAX Integer32 (0..6000)
            MAX-ACCESS read-write
            STATUS current
            DESCRIPTION
                "Low-voltage power-off disconnected time, It can be configured by users, and its value is an integer (1). 
                    Here, if lvd mode is time mode, value range defines between 0 to 6000, unit: minutes(min). If the value is 2147483647(0x7FFFFFFF), it indicates that the value is invalid.
                NOTE: Only the lvd in time power off mode, this parameter can be configured successfully."
            ::= { hwSiteIDCDUSetEntry 18 }

        hwIDCDULoad1LvdTime OBJECT-TYPE
            SYNTAX Integer32 (0..6000)
            MAX-ACCESS read-write
            STATUS current
            DESCRIPTION
                "Low-voltage power-off load1 disconnected time, It can be configured by users, and its value is an integer (1). 
                    Here, if lvd mode is time mode, value range defines between 0 to 6000, unit: minutes(min). If the value is 2147483647(0x7FFFFFFF), it indicates that the value is invalid.
                NOTE: Only the lvd in time power off mode, this parameter can be configured successfully."
            ::= { hwSiteIDCDUSetEntry 19 }

        hwIDCDULoad2LvdTime OBJECT-TYPE
            SYNTAX Integer32 (0..6000)
            MAX-ACCESS read-write
            STATUS current
            DESCRIPTION
                "Low-voltage power-off load2 disconnected time, It can be configured by users, and its value is an integer (1). 
                    Here, if lvd mode is time mode, value range defines between 0 to 6000, unit: minutes(min). If the value is 2147483647(0x7FFFFFFF), it indicates that the value is invalid.
                NOTE: Only the lvd in time power off mode, this parameter can be configured successfully."
            ::= { hwSiteIDCDUSetEntry 20 }

        hwIDCDULoad3LvdTime OBJECT-TYPE
            SYNTAX Integer32 (0..6000)
            MAX-ACCESS read-write
            STATUS current
            DESCRIPTION
                "Low-voltage power-off load3 disconnected time, It can be configured by users, and its value is an integer (1). 
                    Here, if lvd mode is time mode, value range defines between 0 to 6000, unit: minutes(min). If the value is 2147483647(0x7FFFFFFF), it indicates that the value is invalid.
                NOTE: Only the lvd in time power off mode, this parameter can be configured successfully."
            ::= { hwSiteIDCDUSetEntry 21 }

        hwIDCDULoad4LvdTime OBJECT-TYPE
            SYNTAX Integer32 (0..6000)
            MAX-ACCESS read-write
            STATUS current
            DESCRIPTION
                "Low-voltage power-off load4 disconnected time, It can be configured by users, and its value is an integer (1). 
                    Here, if lvd mode is time mode, value range defines between 0 to 6000, unit: minutes(min). If the value is 2147483647(0x7FFFFFFF), it indicates that the value is invalid.
                NOTE: Only the lvd in time power off mode, this parameter can be configured successfully."
            ::= { hwSiteIDCDUSetEntry 22 }

        hwIDCDUTotalLvdCapacity OBJECT-TYPE
            SYNTAX Unsigned32 (0..99)
            MAX-ACCESS read-write
            STATUS current
            DESCRIPTION
                "Low-capacity power-off disconnecte , It can be configured by users, and its value is an integer (1). 
                    Here, if lvd mode is capacity mode, value range defines between 0 to 99, unit: %. If the value is 2147483647(0x7FFFFFFF), it indicates that the value is invalid.
                NOTE: Only the lvd in capacity power off mode, this parameter can be configured successfully."
            ::= { hwSiteIDCDUSetEntry 23 }

        hwIDCDULoad1LvdCapacity OBJECT-TYPE
            SYNTAX Unsigned32 (0..99)
            MAX-ACCESS read-write
            STATUS current
            DESCRIPTION
                "Low-capacity power-off load1 disconnecte , It can be configured by users, and its value is an integer (1). 
                    Here, if lvd mode is capacity mode, value range defines between 0 to 99, unit: %. If the value is 2147483647(0x7FFFFFFF), it indicates that the value is invalid.
                NOTE: Only the lvd in capacity power off mode, this parameter can be configured successfully."
            ::= { hwSiteIDCDUSetEntry 24 }

        hwIDCDULoad2LvdCapacity OBJECT-TYPE
            SYNTAX Unsigned32 (0..99)
            MAX-ACCESS read-write
            STATUS current
            DESCRIPTION
                "Low-capacity power-off load2 disconnecte , It can be configured by users, and its value is an integer (1). 
                    Here, if lvd mode is capacity mode, value range defines between 0 to 99, unit: %. If the value is 2147483647(0x7FFFFFFF), it indicates that the value is invalid.
                NOTE: Only the lvd in capacity power off mode, this parameter can be configured successfully."
            ::= { hwSiteIDCDUSetEntry 25 }

        hwIDCDULoad3LvdCapacity OBJECT-TYPE
            SYNTAX Unsigned32 (0..99)
            MAX-ACCESS read-write
            STATUS current
            DESCRIPTION
                "Low-capacity power-off load3 disconnecte , It can be configured by users, and its value is an integer (1). 
                    Here, if lvd mode is capacity mode, value range defines between 0 to 99, unit: %. If the value is 2147483647(0x7FFFFFFF), it indicates that the value is invalid.
                NOTE: Only the lvd in capacity power off mode, this parameter can be configured successfully."
            ::= { hwSiteIDCDUSetEntry 26 }

        hwIDCDULoad4LvdCapacity OBJECT-TYPE
            SYNTAX Unsigned32 (0..99)
            MAX-ACCESS read-write
            STATUS current
            DESCRIPTION
                "Low-capacity power-off  load4 disconnecte , It can be configured by users, and its value is an integer (1). 
                    Here, if lvd mode is capacity mode, value range defines between 0 to 99, unit: %. If the value is 2147483647(0x7FFFFFFF), it indicates that the value is invalid.
                NOTE: Only the lvd in capacity power off mode, this parameter can be configured successfully."
            ::= { hwSiteIDCDUSetEntry 27 }

        hwIDCDUTotalLvdPDEnable OBJECT-TYPE
            SYNTAX INTEGER
                {
                no(1),
                yes(2),
                unknown(255)
                }
            MAX-ACCESS read-write
            STATUS current
            DESCRIPTION
                "Specific type of the IDCDU module total load lvd timed enable or not. It is an enumeration type:
                If the enumeration value is 1, it indicates that lvd is disenabled ; 
                If the enumeration value is 2, it indicates that lvd is enabled."
            ::= { hwSiteIDCDUSetEntry 28 }

        hwIDCDULoad1LvdPDEnable OBJECT-TYPE
            SYNTAX INTEGER
                {
                no(1),
                yes(2),
                unknown(255)
                }
            MAX-ACCESS read-write
            STATUS current
            DESCRIPTION
                "Specific type of the IDCDU module  load1 lvd timed enable or not. It is an enumeration type:
                If the enumeration value is 1, it indicates that lvd is disenabled ; 
                If the enumeration value is 2, it indicates that lvd is enabled."
            ::= { hwSiteIDCDUSetEntry 29 }

        hwIDCDULoad2LvdPDEnable OBJECT-TYPE
            SYNTAX INTEGER
                {
                no(1),
                yes(2),
                unknown(255)
                }
            MAX-ACCESS read-write
            STATUS current
            DESCRIPTION
                "Specific type of the IDCDU module  load2 lvd timed enable or not. It is an enumeration type:
                If the enumeration value is 1, it indicates that lvd is disenabled ; 
                If the enumeration value is 2, it indicates that lvd is enabled."
            ::= { hwSiteIDCDUSetEntry 30 }

        hwIDCDULoad3LvdPDEnable OBJECT-TYPE
            SYNTAX INTEGER
                {
                no(1),
                yes(2),
                unknown(255)
                }
            MAX-ACCESS read-write
            STATUS current
            DESCRIPTION
                "Specific type of the IDCDU module  load3 lvd timed enable or not. It is an enumeration type:
                If the enumeration value is 1, it indicates that lvd is disenabled ; 
                If the enumeration value is 2, it indicates that lvd is enabled."
            ::= { hwSiteIDCDUSetEntry 31 }

        hwIDCDULoad4LvdPDEnable OBJECT-TYPE
            SYNTAX INTEGER
                {
                no(1),
                yes(2),
                unknown(255)
                }
            MAX-ACCESS read-write
            STATUS current
            DESCRIPTION
                "Specific type of the IDCDU module  load4 lvd timed enable or not. It is an enumeration type:
                If the enumeration value is 1, it indicates that lvd is disenabled ; 
                If the enumeration value is 2, it indicates that lvd is enabled."
            ::= { hwSiteIDCDUSetEntry 32 }

        hwIDCDUTotalLvdPDTime OBJECT-TYPE
            SYNTAX OCTET STRING (SIZE (0..60))
            MAX-ACCESS read-write
            STATUS current
            DESCRIPTION
                "Timed power-off disconnected, It can be configured by users,"
            ::= { hwSiteIDCDUSetEntry 33 }

        hwIDCDULoad1LvdPDTime OBJECT-TYPE
            SYNTAX OCTET STRING (SIZE (0..60))
            MAX-ACCESS read-write
            STATUS current
            DESCRIPTION
                "Timed power-off load1 disconnected, It can be configured by users,"
            ::= { hwSiteIDCDUSetEntry 34 }

        hwIDCDULoad2LvdPDTime OBJECT-TYPE
            SYNTAX OCTET STRING (SIZE (0..60))
            MAX-ACCESS read-write
            STATUS current
            DESCRIPTION
                "Timed power-off load2 disconnected, It can be configured by users,"
            ::= { hwSiteIDCDUSetEntry 35 }

        hwIDCDULoad3LvdPDTime OBJECT-TYPE
            SYNTAX OCTET STRING (SIZE (0..60))
            MAX-ACCESS read-write
            STATUS current
            DESCRIPTION
                "Timed power-off load3 disconnected, It can be configured by users,"
            ::= { hwSiteIDCDUSetEntry 36 }

        hwIDCDULoad4LvdPDTime OBJECT-TYPE
            SYNTAX OCTET STRING (SIZE (0..60))
            MAX-ACCESS read-write
            STATUS current
            DESCRIPTION
                "Timed power-off load4 disconnected, It can be configured by users,"
            ::= { hwSiteIDCDUSetEntry 37 }

        hwIDCDUTotalLvdPDDuration OBJECT-TYPE
            SYNTAX Integer32 (0..1440)
            MAX-ACCESS read-write
            STATUS current
            DESCRIPTION
                "Timed power-off disconnected times, It can be configured by users, and its value is an integer (1). 
                    Here, if lvd mode is time mode, value range defines between 0 to 1440, unit: minutes(min). If the value is 2147483647(0x7FFFFFFF), it indicates that the value is invalid.
                NOTE: Only the lvd in timed power off mode, this parameter can be configured successfully."
            ::= { hwSiteIDCDUSetEntry 38 }

        hwIDCDULoad1LvdPDDuration OBJECT-TYPE
            SYNTAX Integer32 (0..1440)
            MAX-ACCESS read-write
            STATUS current
            DESCRIPTION
                "Timed power-off load1 disconnected times, It can be configured by users, and its value is an integer (1). 
                    Here, if lvd mode is time mode, value range defines between 0 to 1440, unit: minutes(min). If the value is 2147483647(0x7FFFFFFF), it indicates that the value is invalid.
                NOTE: Only the lvd in timed power off mode, this parameter can be configured successfully."
            ::= { hwSiteIDCDUSetEntry 39 }

        hwIDCDULoad2LvdPDDuration OBJECT-TYPE
            SYNTAX Integer32 (0..1440)
            MAX-ACCESS read-write
            STATUS current
            DESCRIPTION
                "Timed power-off load2 disconnected times, It can be configured by users, and its value is an integer (1). 
                    Here, if lvd mode is time mode, value range defines between 0 to 1440, unit: minutes(min). If the value is 2147483647(0x7FFFFFFF), it indicates that the value is invalid.
                NOTE: Only the lvd in timed power off mode, this parameter can be configured successfully."
            ::= { hwSiteIDCDUSetEntry 40 }

        hwIDCDULoad3LvdPDDuration OBJECT-TYPE
            SYNTAX Integer32 (0..1440)
            MAX-ACCESS read-write
            STATUS current
            DESCRIPTION
                "Timed power-off load3 disconnected times, It can be configured by users, and its value is an integer (1). 
                    Here, if lvd mode is time mode, value range defines between 0 to 1440, unit: minutes(min). If the value is 2147483647(0x7FFFFFFF), it indicates that the value is invalid.
                NOTE: Only the lvd in timed power off mode, this parameter can be configured successfully."
            ::= { hwSiteIDCDUSetEntry 41 }

        hwIDCDULoad4LvdPDDuration OBJECT-TYPE
            SYNTAX Integer32 (0..1440)
            MAX-ACCESS read-write
            STATUS current
            DESCRIPTION
                "Timed power-off load4 disconnected times, It can be configured by users, and its value is an integer (1). 
                    Here, if lvd mode is time mode, value range defines between 0 to 1440, unit: minutes(min). If the value is 2147483647(0x7FFFFFFF), it indicates that the value is invalid.
                NOTE: Only the lvd in timed power off mode, this parameter can be configured successfully."
            ::= { hwSiteIDCDUSetEntry 42 }

        hwIDCDULoadTotalDGOff OBJECT-TYPE
            SYNTAX INTEGER
                {
                disable(1),
                enable(2),
                unknown(255)
                }
            MAX-ACCESS read-write
            STATUS current
            DESCRIPTION
                "DG service enable of the total IDCDU module. It is an enumeration type:
                If the enumeration value is 1, it indicates that lvd is disable; 
                If the enumeration value is 2, it indicates that lvd is enable."
            ::= { hwSiteIDCDUSetEntry 43 }

        hwIDCDULoad1DGOff OBJECT-TYPE
            SYNTAX INTEGER
                {
                disable(1),
                enable(2),
                unknown(255)
                }
            MAX-ACCESS read-write
            STATUS current
            DESCRIPTION
                "DG service enable of the IDCDU module load 1. It is an enumeration type:
                If the enumeration value is 1, it indicates that lvd is disable; 
                If the enumeration value is 2, it indicates that lvd is enable."
            ::= { hwSiteIDCDUSetEntry 44 }

        hwIDCDULoad2DGOff OBJECT-TYPE
            SYNTAX INTEGER
                {
                disable(1),
                enable(2),
                unknown(255)
                }
            MAX-ACCESS read-write
            STATUS current
            DESCRIPTION
                "DG service enable of the IDCDU module load 2. It is an enumeration type:
                If the enumeration value is 1, it indicates that lvd is disable; 
                If the enumeration value is 2, it indicates that lvd is enable."
            ::= { hwSiteIDCDUSetEntry 45 }

        hwIDCDULoad3DGOff OBJECT-TYPE
            SYNTAX INTEGER
                {
                disable(1),
                enable(2),
                unknown(255)
                }
            MAX-ACCESS read-write
            STATUS current
            DESCRIPTION
                "DG service enable of the IDCDU module load 3. It is an enumeration type:
                If the enumeration value is 1, it indicates that lvd is disable; 
                If the enumeration value is 2, it indicates that lvd is enable."
            ::= { hwSiteIDCDUSetEntry 46 }

        hwIDCDULoad4DGOff OBJECT-TYPE
            SYNTAX INTEGER
                {
                disable(1),
                enable(2),
                unknown(255)
                }
            MAX-ACCESS read-write
            STATUS current
            DESCRIPTION
                "DG service enable of the IDCDU module load 4. It is an enumeration type:
                If the enumeration value is 1, it indicates that lvd is disable; 
                If the enumeration value is 2, it indicates that lvd is enable."
            ::= { hwSiteIDCDUSetEntry 47 }

        hwIDCDULoad1LvdMode OBJECT-TYPE
            SYNTAX INTEGER
                {
                voltageMode(1),
                timeMode(2),
                capacityMode(3),
                consumptionMode(4),
                unknown(255)
                }
            MAX-ACCESS read-write
            STATUS current
            DESCRIPTION
                "Specific type of the IDCDU module load 1 lvd mode. It is an enumeration type:
                If the enumeration value is 1, it indicates voltage mode; 
                If the enumeration value is 2, it indicates time mode;
                If the enumeration value is 3, it indicates capacity mode;
                If the enumeration value is 4, it indicates consumption mode."
            ::= { hwSiteIDCDUSetEntry 48 }

        hwIDCDULoad2LvdMode OBJECT-TYPE
            SYNTAX INTEGER
                {
                voltageMode(1),
                timeMode(2),
                capacityMode(3),
                consumptionMode(4),
                unknown(255)
                }
            MAX-ACCESS read-write
            STATUS current
            DESCRIPTION
                "Specific type of the IDCDU module load 2 lvd mode. It is an enumeration type:
                If the enumeration value is 1, it indicates voltage mode; 
                If the enumeration value is 2, it indicates time mode;
                If the enumeration value is 3, it indicates capacity mode;
                If the enumeration value is 4, it indicates consumption mode."
            ::= { hwSiteIDCDUSetEntry 49 }

        hwIDCDULoad3LvdMode OBJECT-TYPE
            SYNTAX INTEGER
                {
                voltageMode(1),
                timeMode(2),
                capacityMode(3),
                consumptionMode(4),
                unknown(255)
                }
            MAX-ACCESS read-write
            STATUS current
            DESCRIPTION
                "Specific type of the IDCDU module load 3 lvd mode. It is an enumeration type:
                If the enumeration value is 1, it indicates voltage mode; 
                If the enumeration value is 2, it indicates time mode;
                If the enumeration value is 3, it indicates capacity mode;
                If the enumeration value is 4, it indicates consumption mode."
            ::= { hwSiteIDCDUSetEntry 50 }

        hwIDCDULoad4LvdMode OBJECT-TYPE
            SYNTAX INTEGER
                {
                voltageMode(1),
                timeMode(2),
                capacityMode(3),
                consumptionMode(4),
                unknown(255)
                }
            MAX-ACCESS read-write
            STATUS current
            DESCRIPTION
                "Specific type of the IDCDU module load 4 lvd mode. It is an enumeration type:
                If the enumeration value is 1, it indicates voltage mode; 
                If the enumeration value is 2, it indicates time mode;
                If the enumeration value is 3, it indicates capacity mode;
                If the enumeration value is 4, it indicates consumption mode."
            ::= { hwSiteIDCDUSetEntry 51 }

        hwIDCDUTotalLoadOverCurrent OBJECT-TYPE
            SYNTAX Unsigned32 (30..300)
            MAX-ACCESS read-write
            STATUS current
            DESCRIPTION
                "Total load over current of IDCDU. Value range: 3 to 30, unit: A, and the value is accurate to one decimal place (.1)."
            ::= { hwSiteIDCDUSetEntry 52 }

        hwIDCDULoad1OverCurrent OBJECT-TYPE
            SYNTAX Unsigned32 (30..300)
            MAX-ACCESS read-write
            STATUS current
            DESCRIPTION
                "Load 1 over current point of IDCDU. Value range: 3 to 30, unit: A, and the value is accurate to one decimal place (.1)."
            ::= { hwSiteIDCDUSetEntry 53 }

        hwIDCDULoad2OverCurrent OBJECT-TYPE
            SYNTAX Unsigned32 (30..300)
            MAX-ACCESS read-write
            STATUS current
            DESCRIPTION
                "Load 2 over current point of IDCDU. Value range: 3 to 30, unit: A, and the value is accurate to one decimal place (.1)."
            ::= { hwSiteIDCDUSetEntry 54 }

        hwIDCDULoad3OverCurrent OBJECT-TYPE
            SYNTAX Unsigned32 (30..300)
            MAX-ACCESS read-write
            STATUS current
            DESCRIPTION
                "Load 3 over current point of IDCDU. Value range:3 to 30, unit: A, and the value is accurate to one decimal place (.1)."
            ::= { hwSiteIDCDUSetEntry 55 }

        hwIDCDULoad4OverCurrent OBJECT-TYPE
            SYNTAX Unsigned32 (30..300)
            MAX-ACCESS read-write
            STATUS current
            DESCRIPTION
                "Load 4 over current point of IDCDU. Value range: 3 to 30, unit: A, and the value is accurate to one decimal place (.1)."
            ::= { hwSiteIDCDUSetEntry 56 }

        hwIDCDUTotalLoadOffConsum OBJECT-TYPE
            SYNTAX Unsigned32 (0..10000000)
            MAX-ACCESS read-write
            STATUS current
            DESCRIPTION
                "Total load offline power consumtion of IDCDU. Value range: 0 to 10000000, unit: kWh, and the value is accurate to two decimal place (.01)."
            ::= { hwSiteIDCDUSetEntry 57 }

        hwIDCDULoad1OffConsum OBJECT-TYPE
            SYNTAX Unsigned32 (0..10000000)
            MAX-ACCESS read-write
            STATUS current
            DESCRIPTION
                "load 1 offline power consumtion of IDCDU. Value range: 0 to 10000000, unit: kWh, and the value is accurate to two decimal place (.01)."
            ::= { hwSiteIDCDUSetEntry 58 }

        hwIDCDULoad2OffConsum OBJECT-TYPE
            SYNTAX Unsigned32 (0..10000000)
            MAX-ACCESS read-write
            STATUS current
            DESCRIPTION
                "load 2 offline power consumtion of IDCDU. Value range: 0 to 10000000, unit: kWh, and the value is accurate to two decimal place (.01)."
            ::= { hwSiteIDCDUSetEntry 59 }

        hwIDCDULoad3OffConsum OBJECT-TYPE
            SYNTAX Unsigned32 (0..10000000)
            MAX-ACCESS read-write
            STATUS current
            DESCRIPTION
                "load 3 offline power consumtion of IDCDU. Value range: 0 to 10000000, unit: kWh, and the value is accurate to two decimal place (.01)."
            ::= { hwSiteIDCDUSetEntry 60 }

        hwIDCDULoad4OffConsum OBJECT-TYPE
            SYNTAX Unsigned32 (0..10000000)
            MAX-ACCESS read-write
            STATUS current
            DESCRIPTION
                "load 4 offline power consumtion of IDCDU. Value range: 0 to 10000000, unit: kWh, and the value is accurate to two decimal place (.01)."
            ::= { hwSiteIDCDUSetEntry 61 }

        hwIDCDULoadUserCfg OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "User configuration of the Idcdu load"
            ::= { hwSiteIDCDUSetEntry 62 }

        hwIDCDULoad1UserCfg OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "User configuration of the Idcdu load 1 "
            ::= { hwSiteIDCDUSetEntry 63 }

        hwIDCDULoad2UserCfg OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "User configuration of the Idcdu load 2"
            ::= { hwSiteIDCDUSetEntry 64 }

        hwIDCDULoad3UserCfg OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "User configuration of the Idcdu load 3"
            ::= { hwSiteIDCDUSetEntry 65 }

        hwIDCDULoad4UserCfg OBJECT-TYPE
            SYNTAX INTEGER
                {
                none(1),
                user1(2),
                user2(3),
                user3(4),
                user4(5),
                user5(6),
                user6(7),
                user7(8),
                user8(9),
                user9(10),
                user10(11),
                user11(12),
                user12(13),
                user13(14),
                user14(15),
                user15(16),
                user16(17),
                user17(18),
                user18(19),
                user19(20),
                user20(21),
                user21(22),
                user22(23),
                user23(24),
                user24(25),
                user25(26),
                user26(27),
                user27(28),
                user28(29),
                user29(30),
                user30(31),
                unknown(255)
                }
            MAX-ACCESS read-write
            STATUS current
            DESCRIPTION
                "User configuration of the Idcdu load 4"
            ::= { hwSiteIDCDUSetEntry 66 }

        hwIDCDULoad1BranchCfg OBJECT-TYPE
            SYNTAX INTEGER
                {
                none(1),
                branch1(2),
                branch2(3),
                branch3(4),
                branch4(5),
                branch5(6),
                branch6(7),
                branch7(8),
                branch8(9),
                branch9(10),
                branch10(11),
                unknown(255)
                }
            MAX-ACCESS read-write
            STATUS current
            DESCRIPTION
                "Branch configuration of the Idcdu load 1 "
            ::= { hwSiteIDCDUSetEntry 67 }

        hwIDCDULoad2BranchCfg OBJECT-TYPE
            SYNTAX INTEGER
                {
                none(1),
                branch1(2),
                branch2(3),
                branch3(4),
                branch4(5),
                branch5(6),
                branch6(7),
                branch7(8),
                branch8(9),
                branch9(10),
                branch10(11),
                unknown(255)
                }
            MAX-ACCESS read-write
            STATUS current
            DESCRIPTION
                "Branch configuration of the Idcdu load 2"
            ::= { hwSiteIDCDUSetEntry 68 }

        hwIDCDULoad3BranchCfg OBJECT-TYPE
            SYNTAX INTEGER
                {
                none(1),
                branch1(2),
                branch2(3),
                branch3(4),
                branch4(5),
                branch5(6),
                branch6(7),
                branch7(8),
                branch8(9),
                branch9(10),
                branch10(11),
                unknown(255)
                }
            MAX-ACCESS read-write
            STATUS current
            DESCRIPTION
                "Branch configuration of the Idcdu load 3"
            ::= { hwSiteIDCDUSetEntry 69 }

        hwIDCDULoad4BranchCfg OBJECT-TYPE
            SYNTAX INTEGER
                {
                none(1),
                branch1(2),
                branch2(3),
                branch3(4),
                branch4(5),
                branch5(6),
                branch6(7),
                branch7(8),
                branch8(9),
                branch9(10),
                branch10(11),
                unknown(255)
                }
            MAX-ACCESS read-write
            STATUS current
            DESCRIPTION
                "Branch configuration of the Idcdu load 4"
            ::= { hwSiteIDCDUSetEntry 70 }

        hwIDCDULoadPDStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 71 }

        hwIDCDULoad1PDStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 72 }

        hwIDCDULoad2PDStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 73 }

        hwIDCDULoad3PDStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 74 }

        hwIDCDULoad4PDStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 75 }

        hwIDCDULoadPDDuration2 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 76 }

        hwIDCDULoad1PDDuration2 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 77 }

        hwIDCDULoad2PDDuration2 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 78 }

        hwIDCDULoad3PDDuration2 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 79 }

        hwIDCDULoad4PDDuration2 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 80 }

        hwIDCDULoadPDStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 81 }

        hwIDCDULoad1PDStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 82 }

        hwIDCDULoad2PDStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 83 }

        hwIDCDULoad3PDStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 84 }

        hwIDCDULoad4PDStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 85 }

        hwIDCDULoadPDDuration3 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 86 }

        hwIDCDULoad1PDDuration3 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 87 }

        hwIDCDULoad2PDDuration3 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 88 }

        hwIDCDULoad3PDDuration3 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 89 }

        hwIDCDULoad4PDDuration3 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 90 }

        hwIDCDULoadPDStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 91 }

        hwIDCDULoad1PDStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 92 }

        hwIDCDULoad2PDStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 93 }

        hwIDCDULoad3PDStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 94 }

        hwIDCDULoad4PDStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 95 }

        hwIDCDULoadPDDuration4 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 96 }

        hwIDCDULoad1PDDuration4 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 97 }

        hwIDCDULoad2PDDuration4 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 98 }

        hwIDCDULoad3PDDuration4 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 99 }

        hwIDCDULoad4PDDuration4 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 100 }

        hwIDCDULoadPDStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 101 }

        hwIDCDULoad1PDStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 102 }

        hwIDCDULoad2PDStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 103 }

        hwIDCDULoad3PDStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 104 }

        hwIDCDULoad4PDStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 105 }

        hwIDCDULoadPDDuration5 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 106 }

        hwIDCDULoad1PDDuration5 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 107 }

        hwIDCDULoad2PDDuration5 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 108 }

        hwIDCDULoad3PDDuration5 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 109 }

        hwIDCDULoad4PDDuration5 OBJECT-TYPE
            SYNTAX Unsigned32 (1..1440)
            MAX-ACCESS read-write
            STATUS current
            DESCRIPTION
                "llvd duration of IDCDU. Value range: 0 to 63, unit: NA, and the value is accurate to zero decimal place (1.)."
            ::= { hwSiteIDCDUSetEntry 110 }

        hwIDCDUExemptPeriodNoBK OBJECT-TYPE
            SYNTAX INTEGER
                {
                no(1),
                yes(2),
                unknown(255)
                }
            MAX-ACCESS read-write
            STATUS current
            DESCRIPTION
                "Exempt Period No Backup Function Enable"
            ::= { hwSiteIDCDUSetEntry 111 }

        hwIDCDUExemptPeriodNoBK1 OBJECT-TYPE
            SYNTAX INTEGER
                {
                no(1),
                yes(2),
                unknown(255)
                }
            MAX-ACCESS read-write
            STATUS current
            DESCRIPTION
                "Exempt Period No Backup Function Enable for load 1"
            ::= { hwSiteIDCDUSetEntry 112 }

        hwIDCDUExemptPeriodNoBK2 OBJECT-TYPE
            SYNTAX INTEGER
                {
                no(1),
                yes(2),
                unknown(255)
                }
            MAX-ACCESS read-write
            STATUS current
            DESCRIPTION
                "Exempt Period No Backup Function Enable for load 2"
            ::= { hwSiteIDCDUSetEntry 113 }

        hwIDCDUExemptPeriodNoBK3 OBJECT-TYPE
            SYNTAX INTEGER
                {
                no(1),
                yes(2),
                unknown(255)
                }
            MAX-ACCESS read-write
            STATUS current
            DESCRIPTION
                "Exempt Period No Backup Function Enable for load 3"
            ::= { hwSiteIDCDUSetEntry 114 }

        hwIDCDUExemptPeriodNoBK4 OBJECT-TYPE
            SYNTAX INTEGER
                {
                no(1),
                yes(2),
                unknown(255)
                }
            MAX-ACCESS read-write
            STATUS current
            DESCRIPTION
                "Exempt Period No Backup Function Enable for load 4"
            ::= { hwSiteIDCDUSetEntry 115 }

        hwIDCDULoadExemptPeriodStartTime1 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 116 }

        hwIDCDULoad1ExemptPeriodStartTime1 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 117 }

        hwIDCDULoad2ExemptPeriodStartTime1 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 118 }

        hwIDCDULoad3ExemptPeriodStartTime1 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 119 }

        hwIDCDULoad4ExemptPeriodStartTime1 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 120 }

        hwIDCDULoadExemptPeriodDuration1 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 121 }

        hwIDCDULoad1ExemptPeriodDuration1 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 122 }

        hwIDCDULoad2ExemptPeriodDuration1 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 123 }

        hwIDCDULoad3ExemptPeriodDuration1 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 124 }

        hwIDCDULoad4ExemptPeriodDuration1 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 125 }

        hwIDCDULoadExemptPeriodStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 126 }

        hwIDCDULoad1ExemptPeriodStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 127 }

        hwIDCDULoad2ExemptPeriodStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 128 }

        hwIDCDULoad3ExemptPeriodStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 129 }

        hwIDCDULoad4ExemptPeriodStartTime2 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 130 }

        hwIDCDULoadExemptPeriodDuration2 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 131 }

        hwIDCDULoad1ExemptPeriodDuration2 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 132 }

        hwIDCDULoad2ExemptPeriodDuration2 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 133 }

        hwIDCDULoad3ExemptPeriodDuration2 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 134 }

        hwIDCDULoad4ExemptPeriodDuration2 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 135 }

        hwIDCDULoadExemptPeriodStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 136 }

        hwIDCDULoad1ExemptPeriodStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 137 }

        hwIDCDULoad2ExemptPeriodStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 138 }

        hwIDCDULoad3ExemptPeriodStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 139 }

        hwIDCDULoad4ExemptPeriodStartTime3 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 140 }

        hwIDCDULoadExemptPeriodDuration3 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 141 }

        hwIDCDULoad1ExemptPeriodDuration3 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 142 }

        hwIDCDULoad2ExemptPeriodDuration3 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 143 }

        hwIDCDULoad3ExemptPeriodDuration3 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 144 }

        hwIDCDULoad4ExemptPeriodDuration3 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 145 }

        hwIDCDULoadExemptPeriodStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 146 }

        hwIDCDULoad1ExemptPeriodStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 147 }

        hwIDCDULoad2ExemptPeriodStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 148 }

        hwIDCDULoad3ExemptPeriodStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 149 }

        hwIDCDULoad4ExemptPeriodStartTime4 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 150 }

        hwIDCDULoadExemptPeriodDuration4 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 151 }

        hwIDCDULoad1ExemptPeriodDuration4 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 152 }

        hwIDCDULoad2ExemptPeriodDuration4 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 153 }

        hwIDCDULoad3ExemptPeriodDuration4 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 154 }

        hwIDCDULoad4ExemptPeriodDuration4 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 155 }

        hwIDCDULoadExemptPeriodStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 156 }

        hwIDCDULoad1ExemptPeriodStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 157 }

        hwIDCDULoad2ExemptPeriodStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 158 }

        hwIDCDULoad3ExemptPeriodStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 159 }

        hwIDCDULoad4ExemptPeriodStartTime5 OBJECT-TYPE
            SYNTAX OCTET STRING (SIZE (0..60))
            MAX-ACCESS read-write
            STATUS current
            DESCRIPTION
                "Start time of IDCDU. Value range: 0 to 63, unit: NA, and the value is accurate to zero decimal place (1.)."
            ::= { hwSiteIDCDUSetEntry 160 }

        hwIDCDULoadExemptPeriodDuration5 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 161 }

        hwIDCDULoad1ExemptPeriodDuration5 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 162 }

        hwIDCDULoad2ExemptPeriodDuration5 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 163 }

        hwIDCDULoad3ExemptPeriodDuration5 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 164 }

        hwIDCDULoad4ExemptPeriodDuration5 OBJECT-TYPE
            SYNTAX Unsigned32 (1..1440)
            MAX-ACCESS read-write
            STATUS current
            DESCRIPTION
                "Exempt Period Duration of IDCDU. Value range: 0 to 63, unit: NA, and the value is accurate to zero decimal place (1.)."
            ::= { hwSiteIDCDUSetEntry 165 }

        hwIDCDULoadPeakShavingEnable OBJECT-TYPE
            SYNTAX INTEGER
                {
                no(1),
                yes(2),
                unknown(255)
                }
            MAX-ACCESS read-write
            STATUS current
            DESCRIPTION
                "IDCDU Load Peak Shaving Enable"
            ::= { hwSiteIDCDUSetEntry 166 }

        hwIDCDULoad1PeakShavingEnable OBJECT-TYPE
            SYNTAX INTEGER
                {
                no(1),
                yes(2),
                unknown(255)
                }
            MAX-ACCESS read-write
            STATUS current
            DESCRIPTION
                "IDCDU Load 1 Peak Shaving Enable"
            ::= { hwSiteIDCDUSetEntry 167 }

        hwIDCDULoad2PeakShavingEnable OBJECT-TYPE
            SYNTAX INTEGER
                {
                no(1),
                yes(2),
                unknown(255)
                }
            MAX-ACCESS read-write
            STATUS current
            DESCRIPTION
                "IDCDU Load 2 Peak Shaving Enable"
            ::= { hwSiteIDCDUSetEntry 168 }

        hwIDCDULoad3PeakShavingEnable OBJECT-TYPE
            SYNTAX INTEGER
                {
                no(1),
                yes(2),
                unknown(255)
                }
            MAX-ACCESS read-write
            STATUS current
            DESCRIPTION
                "IDCDU Load 3 Peak Shaving Enable"
            ::= { hwSiteIDCDUSetEntry 169 }

        hwIDCDULoad4PeakShavingEnable OBJECT-TYPE
            SYNTAX INTEGER
                {
                no(1),
                yes(2),
                unknown(255)
                }
            MAX-ACCESS read-write
            STATUS current
            DESCRIPTION
                "IDCDU Load 4 Peak Shaving Enable"
            ::= { hwSiteIDCDUSetEntry 170 }

        hwSiteUserEquipment OBJECT IDENTIFIER ::= { hwSiteMonitorMIBObjects 54 }

        hwUserEquipmentSampTable OBJECT-TYPE
            SYNTAX SEQUENCE OF HwUserEquipmentSampEntry
            MAX-ACCESS not-accessible
             STATUS current
             DESCRIPTION
                "/"
            ::= { hwSiteUserEquipment 1 }

        hwUserEquipmentSampEntry OBJECT-TYPE
                        SYNTAX HwUserEquipmentSampEntry
            MAX-ACCESS not-accessible
             STATUS current
             DESCRIPTION
                "/"
            INDEX { hwUserEquipmentIndex }
            ::= { hwUserEquipmentSampTable 1 }

        HwUserEquipmentSampEntry            ::= SEQUENCE {
                hwUserEquipmentIndex
                    Integer32,
                hwUserEquipmentEquipID
                    Unsigned32,
                hwUserEquipmentEquipName
                    OCTET STRING,
                hwUserEquipmentTotalCurrent
                    Unsigned32,
                hwUserEquipmentTotalPower
                    Unsigned32,
                hwUserEquipmentTotalConsum
                    Unsigned32
            }

        hwUserEquipmentIndex OBJECT-TYPE
            SYNTAX Integer32 (1..256)
            MAX-ACCESS read-only
            STATUS current
            DESCRIPTION
                "User Equipment table index. Lines of the device list are restricted by the quantity of User Equipment."
            ::= { hwUserEquipmentSampEntry 1 }

        hwUserEquipmentEquipID OBJECT-TYPE
            SYNTAX Unsigned32
            MAX-ACCESS read-only
            STATUS current
            DESCRIPTION
                "User Equipment device ID"
            ::= { hwUserEquipmentSampEntry 2 }

        hwUserEquipmentEquipName OBJECT-TYPE
            SYNTAX OCTET STRING (SIZE (0..63))
            MAX-ACCESS read-only
            STATUS current
            DESCRIPTION
                "User Equipment device Name"
            ::= { hwUserEquipmentSampEntry 3 }

        hwUserEquipmentTotalCurrent OBJECT-TYPE
            SYNTAX Unsigned32 (0..300000)
            MAX-ACCESS read-only
            STATUS current
            DESCRIPTION
                "Total output current of user equipment. Value range: 0.0 to 30000.0, unit: A, and the value is accurate to one decimal place (.1)."
            ::= { hwUserEquipmentSampEntry 4 }

        hwUserEquipmentTotalPower OBJECT-TYPE
            SYNTAX Unsigned32 (0..300000)
            MAX-ACCESS read-only
            STATUS current
            DESCRIPTION
                "Total output power of user equipment. Value range: 0 to 300000, unit: kW, and the value is accurate to two decimal place (.02)."
            ::= { hwUserEquipmentSampEntry 5 }

        hwUserEquipmentTotalConsum OBJECT-TYPE
            SYNTAX Unsigned32 (0..4294967295)
            MAX-ACCESS read-only
            STATUS current
            DESCRIPTION
                "Total power consumtion of user equipment. Value range: 0 to 429496729500, unit: kWh, and the value is accurate to two decimal place (.02)."
            ::= { hwUserEquipmentSampEntry 6 }

        hwUserEquipmentSetTable OBJECT-TYPE
            SYNTAX SEQUENCE OF HwUserEquipmentSetEntry
            MAX-ACCESS not-accessible
             STATUS current
             DESCRIPTION
                "/"
            ::= { hwSiteUserEquipment 2 }

        hwUserEquipmentSetEntry OBJECT-TYPE
                        SYNTAX HwUserEquipmentSetEntry
            MAX-ACCESS not-accessible
             STATUS current
             DESCRIPTION
                "/"
            INDEX { hwUserEquipmentSetConfigurableTag }
            ::= { hwUserEquipmentSetTable 1 }

        HwUserEquipmentSetEntry            ::= SEQUENCE {
                hwUserEquipmentSetConfigurableTag
                    OCTET STRING,
                hwUserEquipmentSetConfigurableID
                    Unsigned32,
                hwUserEquipmentSetPowerOffEnable
                    INTEGER,
                hwUserEquipmentSetLLVDMode
                    INTEGER,
                hwUserEquipmentSetLLVDVoltage
                    Unsigned32,
                hwUserEquipmentSetLLVDOnVoltage
                    Unsigned32,
                hwUserEquipmentSetLLVDTime
                    Unsigned32,
                hwUserEquipmentSetLLVDCapacity
                    Unsigned32,
                hwUserEquipmentSetLLVDPower
                    Unsigned32,
                hwUserEquipmentSetPowerOffOverTempEnable
                    INTEGER,
                hwUserEquipmentSetPowerOffOverTempValue
                    Unsigned32,
                hwUserEquipmentSetPeakShavingEnable
                    INTEGER,
                hwUserEquipmentSetTimingOnOffEnable
                    INTEGER,
                hwUserEquipmentSetTimingOnOff1Enable
                    INTEGER,
                hwUserEquipmentSetTimingOnOff2Enable
                    INTEGER,
                hwUserEquipmentSetTimingOnOff3Enable
                    INTEGER,
                hwUserEquipmentSetTimingOnOff4Enable
                    INTEGER,
                hwUserEquipmentSetTimingOnOff5Enable
                    INTEGER,
                hwUserEquipmentSetTimingOnOff1StartTime
                    OCTET STRING,
                hwUserEquipmentSetTimingOnOff1EndTime
                    OCTET STRING,
                hwUserEquipmentSetTimingOnOff1Duration
                    Unsigned32,
                hwUserEquipmentSetTimingOnOff2StartTime
                    OCTET STRING,
                hwUserEquipmentSetTimingOnOff2EndTime
                    OCTET STRING,
                hwUserEquipmentSetTimingOnOff2Duration
                    Unsigned32,
                hwUserEquipmentSetTimingOnOff3StartTime
                    OCTET STRING,
                hwUserEquipmentSetTimingOnOff3EndTime
                    OCTET STRING,
                hwUserEquipmentSetTimingOnOff3Duration
                    Unsigned32,
                hwUserEquipmentSetTimingOnOff4StartTime
                    OCTET STRING,
                hwUserEquipmentSetTimingOnOff4EndTime
                    OCTET STRING,
                hwUserEquipmentSetTimingOnOff4Duration
                    Unsigned32,
                hwUserEquipmentSetTimingOnOff5StartTime
                    OCTET STRING,
                hwUserEquipmentSetTimingOnOff5EndTime
                    OCTET STRING,
                hwUserEquipmentSetTimingOnOff5Duration
                    Unsigned32,
                hwUserEquipmentSetExemptPeriodOnOffEnable
                    INTEGER,
                hwUserEquipmentSetExemptPeriod1OnOffEnable
                    INTEGER,
                hwUserEquipmentSetExemptPeriod2OnOffEnable
                    INTEGER,
                hwUserEquipmentSetExemptPeriod3OnOffEnable
                    INTEGER,
                hwUserEquipmentSetExemptPeriod4OnOffEnable
                    INTEGER,
                hwUserEquipmentSetExemptPeriod5OnOffEnable
                    INTEGER,
                hwUserEquipmentSetExemptPeriod1OnOffStartTime
                    OCTET STRING,
                hwUserEquipmentSetExemptPeriod1OnOffEndTime
                    OCTET STRING,
                hwUserEquipmentSetExemptPeriod1OnOffDuration
                    Unsigned32,
                hwUserEquipmentSetExemptPeriod2OnOffStartTime
                    OCTET STRING,
                hwUserEquipmentSetExemptPeriod2OnOffEndTime
                    OCTET STRING,
                hwUserEquipmentSetExemptPeriod2OnOffDuration
                    Unsigned32,
                hwUserEquipmentSetExemptPeriod3OnOffStartTime
                    OCTET STRING,
                hwUserEquipmentSetExemptPeriod3OnOffEndTime
                    OCTET STRING,
                hwUserEquipmentSetExemptPeriod3OnOffDuration
                    Unsigned32,
                hwUserEquipmentSetExemptPeriod4OnOffStartTime
                    OCTET STRING,
                hwUserEquipmentSetExemptPeriod4OnOffEndTime
                    OCTET STRING,
                hwUserEquipmentSetExemptPeriod4OnOffDuration
                    Unsigned32,
                hwUserEquipmentSetExemptPeriod5OnOffStartTime
                    OCTET STRING,
                hwUserEquipmentSetExemptPeriod5OnOffEndTime
                    OCTET STRING,
                hwUserEquipmentSetExemptPeriod5OnOffDuration
                    Unsigned32,
                hwUserEquipmentSetDGOff
                    INTEGER
            }

        hwUserEquipmentSetConfigurableTag OBJECT-TYPE
            SYNTAX OCTET STRING (SIZE (0..63))
            MAX-ACCESS read-write
            STATUS current
            DESCRIPTION
                "Configurable Tag of user equipment"
            ::= { hwUserEquipmentSetEntry 1 }

        hwUserEquipmentSetConfigurableID OBJECT-TYPE
            SYNTAX Unsigned32 (0..65535)
            MAX-ACCESS read-write
            STATUS current
            DESCRIPTION
                "Configurable ID of user equipment"
            ::= { hwUserEquipmentSetEntry 2 }

        hwUserEquipmentSetPowerOffEnable OBJECT-TYPE
            SYNTAX INTEGER
                {
                disable(1),
                enable(2),
                unknown(255)
                }
            MAX-ACCESS read-write
            STATUS current
            DESCRIPTION
                "Power off enable switch of user equipment, It is an enumeration type: 
                If the enumeration value is 1, it indicates that the power off function disable;
                If the enumeration value is 2, it indicates that the power off function enable;"
            ::= { hwUserEquipmentSetEntry 3 }

        hwUserEquipmentSetLLVDMode OBJECT-TYPE
            SYNTAX INTEGER
                {
                voltageMode(1),
                timeMode(2),
                capacityMode(3),
                powerMode(4),
                unknown(255)
                }
            MAX-ACCESS read-write
            STATUS current
            DESCRIPTION
                "LLVD mode selection of user equipment, It is an enumeration type: 
                If the enumeration value is 1, it indicates that the voltage LLVD mode;
                If the enumeration value is 2, it indicates that the time LLVD mode;
                If the enumeration value is 3, it indicates that the capacity LLVD mode;
                If the enumeration value is 4, it indicates that the capacity power mode;"
            ::= { hwUserEquipmentSetEntry 4 }

        hwUserEquipmentSetLLVDVoltage OBJECT-TYPE
            SYNTAX Unsigned32 (360..560)
            MAX-ACCESS read-write
            STATUS current
            DESCRIPTION
                "LLVD Voltage control of user equipment. Value range: 360 to 560, unit: V, and the value is accurate to one decimal place (.1)."
            ::= { hwUserEquipmentSetEntry 5 }

        hwUserEquipmentSetLLVDOnVoltage OBJECT-TYPE
            SYNTAX Unsigned32 (370..580)
            MAX-ACCESS read-write
            STATUS current
            DESCRIPTION
                "LLVD On Voltage control of user equipment. Value range: 370 to 580, unit: V, and the value is accurate to one decimal place (.1)."
            ::= { hwUserEquipmentSetEntry 6 }

        hwUserEquipmentSetLLVDTime OBJECT-TYPE
            SYNTAX Unsigned32 (0..6000)
            MAX-ACCESS read-write
            STATUS current
            DESCRIPTION
                "LLVD time control of user equipment. Value range: 0 to 6000, unit: NA, and the value is accurate to one decimal place (.1)."
            ::= { hwUserEquipmentSetEntry 7 }

        hwUserEquipmentSetLLVDCapacity OBJECT-TYPE
            SYNTAX Unsigned32 (0..99)
            MAX-ACCESS read-write
            STATUS current
            DESCRIPTION
                "LLVD time control of user equipment. Value range: 0 to 99, unit: %, and the value is accurate to zero decimal place (.)."
            ::= { hwUserEquipmentSetEntry 8 }

        hwUserEquipmentSetLLVDPower OBJECT-TYPE
            SYNTAX Unsigned32 (0..10000000)
            MAX-ACCESS read-write
            STATUS current
            DESCRIPTION
                "LLVD time control of user equipment. Value range: 0 to 10000000, unit: kWh, and the value is accurate to two decimal place (.01)."
            ::= { hwUserEquipmentSetEntry 9 }

        hwUserEquipmentSetPowerOffOverTempEnable OBJECT-TYPE
            SYNTAX INTEGER
                {
                disable(1),
                enable(2),
                unknown(255)
                }
            MAX-ACCESS read-write
            STATUS current
            DESCRIPTION
                "High temperature LLVD enable switch of user equipment, It is an enumeration type: 
                If the enumeration value is 1, it indicates that the High temperature LLVD function disable;
                If the enumeration value is 2, it indicates that the High temperature LLVD function enable;"
            ::= { hwUserEquipmentSetEntry 10 }

        hwUserEquipmentSetPowerOffOverTempValue OBJECT-TYPE
            SYNTAX Unsigned32 (250..800)
            MAX-ACCESS read-write
            STATUS current
            DESCRIPTION
                "LLVD time control of user equipment. Value range: 250 to 800, unit: degC, and the value is accurate to one decimal place (.1)."
            ::= { hwUserEquipmentSetEntry 11 }

        hwUserEquipmentSetPeakShavingEnable OBJECT-TYPE
            SYNTAX INTEGER
                {
                disable(1),
                enable(2),
                unknown(255)
                }
            MAX-ACCESS read-write
            STATUS current
            DESCRIPTION
                "Peak Shaving enable switch of user equipment, It is an enumeration type: 
                If the enumeration value is 1, it indicates that the Peak Shaving function disable;
                If the enumeration value is 2, it indicates that the Peak Shaving function enable;"
            ::= { hwUserEquipmentSetEntry 12 }

        hwUserEquipmentSetTimingOnOffEnable OBJECT-TYPE
            SYNTAX INTEGER
                {
                disable(1),
                enable(2),
                unknown(255)
                }
            MAX-ACCESS read-write
            STATUS current
            DESCRIPTION
                "Time on enable switch of user equipment, It is an enumeration type: 
                If the enumeration value is 1, it indicates that the time on function disable;
                If the enumeration value is 2, it indicates that the time on function enable;"
            ::= { hwUserEquipmentSetEntry 13 }

        hwUserEquipmentSetTimingOnOff1Enable OBJECT-TYPE
            SYNTAX INTEGER
                {
                disable(1),
                enable(2),
                unknown(255)
                }
            MAX-ACCESS read-write
            STATUS current
            DESCRIPTION
                "Time on 1 enable switch of user equipment, It is an enumeration type: 
                If the enumeration value is 1, it indicates that the time on 1 function disable;
                If the enumeration value is 2, it indicates that the time on 1 function enable;"
            ::= { hwUserEquipmentSetEntry 14 }

        hwUserEquipmentSetTimingOnOff2Enable OBJECT-TYPE
            SYNTAX INTEGER
                {
                disable(1),
                enable(2),
                unknown(255)
                }
            MAX-ACCESS read-write
            STATUS current
            DESCRIPTION
                "Time on 2 enable switch of user equipment, It is an enumeration type: 
                If the enumeration value is 1, it indicates that the time on 2 function disable;
                If the enumeration value is 2, it indicates that the time on 2 function enable;"
            ::= { hwUserEquipmentSetEntry 15 }

        hwUserEquipmentSetTimingOnOff3Enable OBJECT-TYPE
            SYNTAX INTEGER
                {
                disable(1),
                enable(2),
                unknown(255)
                }
            MAX-ACCESS read-write
            STATUS current
            DESCRIPTION
                "Time on 3 enable switch of user equipment, It is an enumeration type: 
                If the enumeration value is 1, it indicates that the time on 3 function disable;
                If the enumeration value is 2, it indicates that the time on 3 function enable;"
            ::= { hwUserEquipmentSetEntry 16 }

        hwUserEquipmentSetTimingOnOff4Enable OBJECT-TYPE
            SYNTAX INTEGER
                {
                disable(1),
                enable(2),
                unknown(255)
                }
            MAX-ACCESS read-write
            STATUS current
            DESCRIPTION
                "Time on 4 enable switch of user equipment, It is an enumeration type: 
                If the enumeration value is 1, it indicates that the time on 4 function disable;
                If the enumeration value is 2, it indicates that the time on 4 function enable;"
            ::= { hwUserEquipmentSetEntry 17 }

        hwUserEquipmentSetTimingOnOff5Enable OBJECT-TYPE
            SYNTAX INTEGER
                {
                disable(1),
                enable(2),
                unknown(255)
                }
            MAX-ACCESS read-write
            STATUS current
            DESCRIPTION
                "Time on 5 enable switch of user equipment, It is an enumeration type: 
                If the enumeration value is 1, it indicates that the time on 5 function disable;
                If the enumeration value is 2, it indicates that the time on 5 function enable;"
            ::= { hwUserEquipmentSetEntry 18 }

        hwUserEquipmentSetTimingOnOff1StartTime OBJECT-TYPE
            SYNTAX OCTET STRING (SIZE (0..60))
            MAX-ACCESS read-write
            STATUS current
            DESCRIPTION
                "Time OnOff start time 1 of user equipment. Value range: 0 to 63, unit: NA, and the value is accurate to zero decimal place (1.)."
            ::= { hwUserEquipmentSetEntry 19 }

        hwUserEquipmentSetTimingOnOff1EndTime OBJECT-TYPE
            SYNTAX OCTET STRING (SIZE (0..60))
            MAX-ACCESS read-write
            STATUS current
            DESCRIPTION
                "Time OnOff end time 1 of user equipment. Value range: 0 to 63, unit: NA, and the value is accurate to zero decimal place (1.)."
            ::= { hwUserEquipmentSetEntry 20 }

        hwUserEquipmentSetTimingOnOff1Duration OBJECT-TYPE
            SYNTAX Unsigned32 (1..1440)
            MAX-ACCESS read-write
            STATUS current
            DESCRIPTION
                "Time OnOff duration 1 of user equipment. Value range: 0 to 1440, unit: NA, and the value is accurate to zero decimal place (1.)."
            ::= { hwUserEquipmentSetEntry 21 }

        hwUserEquipmentSetTimingOnOff2StartTime OBJECT-TYPE
            SYNTAX OCTET STRING (SIZE (0..60))
            MAX-ACCESS read-write
            STATUS current
            DESCRIPTION
                "Time OnOff start time 2 of user equipment. Value range: 0 to 63, unit: NA, and the value is accurate to zero decimal place (1.)."
            ::= { hwUserEquipmentSetEntry 22 }

        hwUserEquipmentSetTimingOnOff2EndTime OBJECT-TYPE
            SYNTAX OCTET STRING (SIZE (0..60))
            MAX-ACCESS read-write
            STATUS current
            DESCRIPTION
                "Time OnOff end time 2 of user equipment. Value range: 0 to 63, unit: NA, and the value is accurate to zero decimal place (1.)."
            ::= { hwUserEquipmentSetEntry 23 }

        hwUserEquipmentSetTimingOnOff2Duration OBJECT-TYPE
            SYNTAX Unsigned32 (1..1440)
            MAX-ACCESS read-write
            STATUS current
            DESCRIPTION
                "Time OnOff duration 2 of user equipment. Value range: 0 to 1440, unit: NA, and the value is accurate to zero decimal place (1.)."
            ::= { hwUserEquipmentSetEntry 24 }

        hwUserEquipmentSetTimingOnOff3StartTime OBJECT-TYPE
            SYNTAX OCTET STRING (SIZE (0..60))
            MAX-ACCESS read-write
            STATUS current
            DESCRIPTION
                "Time OnOff start time 3 of user equipment. Value range: 0 to 63, unit: NA, and the value is accurate to zero decimal place (1.)."
            ::= { hwUserEquipmentSetEntry 25 }

        hwUserEquipmentSetTimingOnOff3EndTime OBJECT-TYPE
            SYNTAX OCTET STRING (SIZE (0..60))
            MAX-ACCESS read-write
            STATUS current
            DESCRIPTION
                "Time OnOff end time 3 of user equipment. Value range: 0 to 63, unit: NA, and the value is accurate to zero decimal place (1.)."
            ::= { hwUserEquipmentSetEntry 26 }

        hwUserEquipmentSetTimingOnOff3Duration OBJECT-TYPE
            SYNTAX Unsigned32 (1..1440)
            MAX-ACCESS read-write
            STATUS current
            DESCRIPTION
                "Time OnOff duration 3 of user equipment. Value range: 0 to 1440, unit: NA, and the value is accurate to zero decimal place (1.)."
            ::= { hwUserEquipmentSetEntry 27 }

        hwUserEquipmentSetTimingOnOff4StartTime OBJECT-TYPE
            SYNTAX OCTET STRING (SIZE (0..60))
            MAX-ACCESS read-write
            STATUS current
            DESCRIPTION
                "Time OnOff start time 4 of user equipment. Value range: 0 to 63, unit: NA, and the value is accurate to zero decimal place (1.)."
            ::= { hwUserEquipmentSetEntry 28 }

        hwUserEquipmentSetTimingOnOff4EndTime OBJECT-TYPE
            SYNTAX OCTET STRING (SIZE (0..60))
            MAX-ACCESS read-write
            STATUS current
            DESCRIPTION
                "Time OnOff end time 4 of user equipment. Value range: 0 to 63, unit: NA, and the value is accurate to zero decimal place (1.)."
            ::= { hwUserEquipmentSetEntry 29 }

        hwUserEquipmentSetTimingOnOff4Duration OBJECT-TYPE
            SYNTAX Unsigned32 (1..1440)
            MAX-ACCESS read-write
            STATUS current
            DESCRIPTION
                "Time OnOff duration 4 of user equipment. Value range: 0 to 1440, unit: NA, and the value is accurate to zero decimal place (1.)."
            ::= { hwUserEquipmentSetEntry 30 }

        hwUserEquipmentSetTimingOnOff5StartTime OBJECT-TYPE
            SYNTAX OCTET STRING (SIZE (0..60))
            MAX-ACCESS read-write
            STATUS current
            DESCRIPTION
                "Time OnOff start time 5 of user equipment. Value range: 0 to 63, unit: NA, and the value is accurate to zero decimal place (1.)."
            ::= { hwUserEquipmentSetEntry 31 }

        hwUserEquipmentSetTimingOnOff5EndTime OBJECT-TYPE
            SYNTAX OCTET STRING (SIZE (0..60))
            MAX-ACCESS read-write
            STATUS current
            DESCRIPTION
                "Time OnOff end time 5 of user equipment. Value range: 0 to 63, unit: NA, and the value is accurate to zero decimal place (1.)."
            ::= { hwUserEquipmentSetEntry 32 }

        hwUserEquipmentSetTimingOnOff5Duration OBJECT-TYPE
            SYNTAX Unsigned32 (1..1440)
            MAX-ACCESS read-write
            STATUS current
            DESCRIPTION
                "Time OnOff duration 5 of user equipment. Value range: 0 to 1440, unit: NA, and the value is accurate to zero decimal place (1.)."
            ::= { hwUserEquipmentSetEntry 33 }

        hwUserEquipmentSetExemptPeriodOnOffEnable OBJECT-TYPE
            SYNTAX INTEGER
                {
                disable(1),
                enable(2),
                unknown(255)
                }
            MAX-ACCESS read-write
            STATUS current
            DESCRIPTION
                "Exempt period OnOff enable switch of user equipment, It is an enumeration type: 
                If the enumeration value is 1, it indicates that the exempt period OnOff function disable;
                If the enumeration value is 2, it indicates that the exempt period OnOff function enable;"
            ::= { hwUserEquipmentSetEntry 34 }

        hwUserEquipmentSetExemptPeriod1OnOffEnable OBJECT-TYPE
            SYNTAX INTEGER
                {
                disable(1),
                enable(2),
                unknown(255)
                }
            MAX-ACCESS read-write
            STATUS current
            DESCRIPTION
                "Exempt period OnOff 1 enable switch of user equipment, It is an enumeration type: 
                If the enumeration value is 1, it indicates that the exempt period OnOff 1 function disable;
                If the enumeration value is 2, it indicates that the exempt period OnOff 1 function enable;"
            ::= { hwUserEquipmentSetEntry 35 }

        hwUserEquipmentSetExemptPeriod2OnOffEnable OBJECT-TYPE
            SYNTAX INTEGER
                {
                disable(1),
                enable(2),
                unknown(255)
                }
            MAX-ACCESS read-write
            STATUS current
            DESCRIPTION
                "Exempt period OnOff 2 enable switch of user equipment, It is an enumeration type: 
                If the enumeration value is 1, it indicates that the exempt period OnOff 2 function disable;
                If the enumeration value is 2, it indicates that the exempt period OnOff 2 function enable;"
            ::= { hwUserEquipmentSetEntry 36 }

        hwUserEquipmentSetExemptPeriod3OnOffEnable OBJECT-TYPE
            SYNTAX INTEGER
                {
                disable(1),
                enable(2),
                unknown(255)
                }
            MAX-ACCESS read-write
            STATUS current
            DESCRIPTION
                "Exempt period OnOff 3 enable switch of user equipment, It is an enumeration type: 
                If the enumeration value is 1, it indicates that the exempt period OnOff 3 function disable;
                If the enumeration value is 2, it indicates that the exempt period OnOff 3 function enable;"
            ::= { hwUserEquipmentSetEntry 37 }

        hwUserEquipmentSetExemptPeriod4OnOffEnable OBJECT-TYPE
            SYNTAX INTEGER
                {
                disable(1),
                enable(2),
                unknown(255)
                }
            MAX-ACCESS read-write
            STATUS current
            DESCRIPTION
                "Exempt period OnOff 4 enable switch of user equipment, It is an enumeration type: 
                If the enumeration value is 1, it indicates that the exempt period OnOff 4 function disable;
                If the enumeration value is 2, it indicates that the exempt period OnOff 4 function enable;"
            ::= { hwUserEquipmentSetEntry 38 }

        hwUserEquipmentSetExemptPeriod5OnOffEnable OBJECT-TYPE
            SYNTAX INTEGER
                {
                disable(1),
                enable(2),
                unknown(255)
                }
            MAX-ACCESS read-write
            STATUS current
            DESCRIPTION
                "Exempt period OnOff 5 enable switch of user equipment, It is an enumeration type: 
                If the enumeration value is 1, it indicates that the exempt period OnOff 5 function disable;
                If the enumeration value is 2, it indicates that the exempt period OnOff 5 function enable;"
            ::= { hwUserEquipmentSetEntry 39 }

        hwUserEquipmentSetExemptPeriod1OnOffStartTime OBJECT-TYPE
            SYNTAX OCTET STRING (SIZE (0..60))
            MAX-ACCESS read-write
            STATUS current
            DESCRIPTION
                "Exempt period 1 OnOff start time of user equipment. Value range: 0 to 63, unit: NA, and the value is accurate to zero decimal place (1.)."
            ::= { hwUserEquipmentSetEntry 40 }

        hwUserEquipmentSetExemptPeriod1OnOffEndTime OBJECT-TYPE
            SYNTAX OCTET STRING (SIZE (0..60))
            MAX-ACCESS read-write
            STATUS current
            DESCRIPTION
                "Exempt period 1 OnOff end time of user equipment. Value range: 0 to 63, unit: NA, and the value is accurate to zero decimal place (1.)."
            ::= { hwUserEquipmentSetEntry 41 }

        hwUserEquipmentSetExemptPeriod1OnOffDuration OBJECT-TYPE
            SYNTAX Unsigned32 (1..1440)
            MAX-ACCESS read-write
            STATUS current
            DESCRIPTION
                "Exempt period 1 OnOff duration of user equipment. Value range: 0 to 1440, unit: NA, and the value is accurate to zero decimal place (1.)."
            ::= { hwUserEquipmentSetEntry 42 }

        hwUserEquipmentSetExemptPeriod2OnOffStartTime OBJECT-TYPE
            SYNTAX OCTET STRING (SIZE (0..60))
            MAX-ACCESS read-write
            STATUS current
            DESCRIPTION
                "Exempt period 2 OnOff start time of user equipment. Value range: 0 to 63, unit: NA, and the value is accurate to zero decimal place (1.)."
            ::= { hwUserEquipmentSetEntry 43 }

        hwUserEquipmentSetExemptPeriod2OnOffEndTime OBJECT-TYPE
            SYNTAX OCTET STRING (SIZE (0..60))
            MAX-ACCESS read-write
            STATUS current
            DESCRIPTION
                "Exempt period 2 OnOff end time of user equipment. Value range: 0 to 63, unit: NA, and the value is accurate to zero decimal place (1.)."
            ::= { hwUserEquipmentSetEntry 44 }

        hwUserEquipmentSetExemptPeriod2OnOffDuration OBJECT-TYPE
            SYNTAX Unsigned32 (1..1440)
            MAX-ACCESS read-write
            STATUS current
            DESCRIPTION
                "Exempt period 2 OnOff duration of user equipment. Value range: 0 to 1440, unit: NA, and the value is accurate to zero decimal place (1.)."
            ::= { hwUserEquipmentSetEntry 45 }

        hwUserEquipmentSetExemptPeriod3OnOffStartTime OBJECT-TYPE
            SYNTAX OCTET STRING (SIZE (0..60))
            MAX-ACCESS read-write
            STATUS current
            DESCRIPTION
                "Exempt period 3 OnOff start time of user equipment. Value range: 0 to 63, unit: NA, and the value is accurate to zero decimal place (1.)."
            ::= { hwUserEquipmentSetEntry 46 }

        hwUserEquipmentSetExemptPeriod3OnOffEndTime OBJECT-TYPE
            SYNTAX OCTET STRING (SIZE (0..60))
            MAX-ACCESS read-write
            STATUS current
            DESCRIPTION
                "Exempt period 3 OnOff end time of user equipment. Value range: 0 to 63, unit: NA, and the value is accurate to zero decimal place (1.)."
            ::= { hwUserEquipmentSetEntry 47 }

        hwUserEquipmentSetExemptPeriod3OnOffDuration OBJECT-TYPE
            SYNTAX Unsigned32 (1..1440)
            MAX-ACCESS read-write
            STATUS current
            DESCRIPTION
                "Exempt period 3 OnOff duration of user equipment. Value range: 0 to 1440, unit: NA, and the value is accurate to zero decimal place (1.)."
            ::= { hwUserEquipmentSetEntry 48 }

        hwUserEquipmentSetExemptPeriod4OnOffStartTime OBJECT-TYPE
            SYNTAX OCTET STRING (SIZE (0..60))
            MAX-ACCESS read-write
            STATUS current
            DESCRIPTION
                "Exempt period 4 OnOff start time of user equipment. Value range: 0 to 63, unit: NA, and the value is accurate to zero decimal place (1.)."
            ::= { hwUserEquipmentSetEntry 49 }

        hwUserEquipmentSetExemptPeriod4OnOffEndTime OBJECT-TYPE
            SYNTAX OCTET STRING (SIZE (0..60))
            MAX-ACCESS read-write
            STATUS current
            DESCRIPTION
                "Exempt period 4 OnOff end time of user equipment. Value range: 0 to 63, unit: NA, and the value is accurate to zero decimal place (1.)."
            ::= { hwUserEquipmentSetEntry 50 }

        hwUserEquipmentSetExemptPeriod4OnOffDuration OBJECT-TYPE
            SYNTAX Unsigned32 (1..1440)
            MAX-ACCESS read-write
            STATUS current
            DESCRIPTION
                "Exempt period 4 OnOff duration of user equipment. Value range: 0 to 1440, unit: NA, and the value is accurate to zero decimal place (1.)."
            ::= { hwUserEquipmentSetEntry 51 }

        hwUserEquipmentSetExemptPeriod5OnOffStartTime OBJECT-TYPE
            SYNTAX OCTET STRING (SIZE (0..60))
            MAX-ACCESS read-write
            STATUS current
            DESCRIPTION
                "Exempt period 5 OnOff start time of user equipment. Value range: 0 to 63, unit: NA, and the value is accurate to zero decimal place (1.)."
            ::= { hwUserEquipmentSetEntry 52 }

        hwUserEquipmentSetExemptPeriod5OnOffEndTime OBJECT-TYPE
            SYNTAX OCTET STRING (SIZE (0..60))
            MAX-ACCESS read-write
            STATUS current
            DESCRIPTION
                "Exempt period 5 OnOff end time of user equipment. Value range: 0 to 63, unit: NA, and the value is accurate to zero decimal place (1.)."
            ::= { hwUserEquipmentSetEntry 53 }

        hwUserEquipmentSetExemptPeriod5OnOffDuration OBJECT-TYPE
            SYNTAX Unsigned32 (1..1440)
            MAX-ACCESS read-write
            STATUS current
            DESCRIPTION
                "Exempt period 5 OnOff duration of user equipment. Value range: 0 to 1440, unit: NA, and the value is accurate to zero decimal place (1.)."
            ::= { hwUserEquipmentSetEntry 54 }

        hwUserEquipmentSetDGOff OBJECT-TYPE
            SYNTAX INTEGER
                {
                disable(1),
                enable(2),
                unknown(255)
                }
            MAX-ACCESS read-write
            STATUS current
            DESCRIPTION
                "DG service of user equipment, It is an enumeration type: 
                If the enumeration value is 1, it indicates that the DG Off;
                If the enumeration value is 2, it indicates that the DG On;"
            ::= { hwUserEquipmentSetEntry 55 }

        hwSiteDCDC24V OBJECT IDENTIFIER ::= { hwSiteMonitorMIBObjects 55 }

        hwDCDC24VGroup OBJECT IDENTIFIER ::= { hwSiteDCDC24V 1 }

        hwDCDC24VGroupSampTable OBJECT-TYPE
            SYNTAX SEQUENCE OF HwDCDC24VGroupSampEntry
            MAX-ACCESS not-accessible
             STATUS current
             DESCRIPTION
                "/"
            ::= { hwDCDC24VGroup 1 }

        hwDCDC24VGroupSampEntry OBJECT-TYPE
                        SYNTAX HwDCDC24VGroupSampEntry
            MAX-ACCESS not-accessible
             STATUS current
             DESCRIPTION
                "/"
            INDEX { hwDCDCGroupEquipID }
            ::= { hwDCDC24VGroupSampTable 1 }

        HwDCDC24VGroupSampEntry            ::= SEQUENCE {
                hwDCDCGroupEquipID
                    Unsigned32,
                hwDCDCGroupEquipName
                    OCTET STRING,
                hwDCDCGroupTotalOutputVoltage
                    Unsigned32,
                hwDCDCGroupTotalOutputCurrent
                    Unsigned32,
                hwDCDCGroupTotalOutputPower
                    Unsigned32
            }

        hwDCDCGroupEquipID OBJECT-TYPE
            SYNTAX Unsigned32
            MAX-ACCESS read-only
            STATUS current
            DESCRIPTION
                "Equip ID of DCDC 24V Group. Value range: 0 to 4294967295, unit: NA, and the value is accurate to zero decimal place (1.)."
            ::= { hwDCDC24VGroupSampEntry 1 }

        hwDCDCGroupEquipName OBJECT-TYPE
            SYNTAX OCTET STRING (SIZE (0..63))
            MAX-ACCESS read-only
            STATUS current
            DESCRIPTION
                "Equip name of DCDC 24V Group. Value range: 0 to 63, unit: NA, and the value is accurate to zero decimal place (1.)."
            ::= { hwDCDC24VGroupSampEntry 2 }

        hwDCDCGroupTotalOutputVoltage OBJECT-TYPE
            SYNTAX Unsigned32 (0..480)
            MAX-ACCESS read-only
            STATUS current
            DESCRIPTION
                "Total output voltage of DCDC 24V Group. Value range: 0 to 480, unit: V, and the value is accurate to zero decimal place (.1)."
            ::= { hwDCDC24VGroupSampEntry 3 }

        hwDCDCGroupTotalOutputCurrent OBJECT-TYPE
            SYNTAX Unsigned32 (0..100000)
            MAX-ACCESS read-only
            STATUS current
            DESCRIPTION
                "Total output current of DCDC 24V Group. Value range: 0 to 100000, unit: A, and the value is accurate to zero decimal place (.1)."
            ::= { hwDCDC24VGroupSampEntry 4 }

        hwDCDCGroupTotalOutputPower OBJECT-TYPE
            SYNTAX Unsigned32 (0..300000)
            MAX-ACCESS read-only
            STATUS current
            DESCRIPTION
                "Total output power of DCDC 24V Group. Value range: 0 to 300000, unit: W, and the value is accurate to zero decimal place (.1)."
            ::= { hwDCDC24VGroupSampEntry 5 }

        hwDCDC24VGroupSetTable OBJECT-TYPE
            SYNTAX SEQUENCE OF HwDCDC24VGroupSetEntry
            MAX-ACCESS not-accessible
             STATUS current
             DESCRIPTION
                "/"
            ::= { hwDCDC24VGroup 2 }

        hwDCDC24VGroupSetEntry OBJECT-TYPE
                        SYNTAX HwDCDC24VGroupSetEntry
            MAX-ACCESS not-accessible
             STATUS current
             DESCRIPTION
                "/"
            INDEX { hwDCDCGroupSetDCOutputVoltage }
            ::= { hwDCDC24VGroupSetTable 1 }

        HwDCDC24VGroupSetEntry            ::= SEQUENCE {
                hwDCDCGroupSetDCOutputVoltage
                    Unsigned32,
                hwDCDCGroupSetOvervoltageThresh
                    Unsigned32,
                hwDCDCGroupSetDeleteEquip
                    INTEGER,
                hwDCDCGroupClearModuleLostAlarm
                    INTEGER,
                hwDCDC24VGroupModuleDelayedStartInterval
                    Unsigned32,
                hwDCDC24VGroupDefaultOutputVoltage
                    Unsigned32
            }

        hwDCDCGroupSetDCOutputVoltage OBJECT-TYPE
            SYNTAX Unsigned32 (240..300)
            MAX-ACCESS read-write
            STATUS current
            DESCRIPTION
                "DC output voltage of DCDC 24V Group. Value range: 240 to 300, unit: V, and the value is accurate to zero decimal place (.1)."
            ::= { hwDCDC24VGroupSetEntry 1 }

        hwDCDCGroupSetOvervoltageThresh OBJECT-TYPE
            SYNTAX Unsigned32 (313..330)
            MAX-ACCESS read-write
            STATUS current
            DESCRIPTION
                "Over voltage threshold of DCDC 24V Group. Value range: 313 to 330, unit: V, and the value is accurate to zero decimal place (.1)."
            ::= { hwDCDC24VGroupSetEntry 2 }

        hwDCDCGroupSetDeleteEquip OBJECT-TYPE
            SYNTAX INTEGER
                {
                yes(2),
                unknown(255)
                }
            MAX-ACCESS read-write
            STATUS current
            DESCRIPTION
                "Set delete equipment of DCDC 24V Group, It is an enumeration type:
                If the enumeration value is 2, it indicates deleting comm fail equipment;"
            ::= { hwDCDC24VGroupSetEntry 3 }

        hwDCDCGroupClearModuleLostAlarm OBJECT-TYPE
            SYNTAX INTEGER
                {
                yes(2),
                unknown(255)
                }
            MAX-ACCESS read-write
            STATUS current
            DESCRIPTION
                "Clear module lost alarm of DCDC 24V Group, It is an enumeration type:
                If the enumeration value is 2, it indicates clearing module lost alarm;"
            ::= { hwDCDC24VGroupSetEntry 4 }

        hwDCDC24VGroupModuleDelayedStartInterval OBJECT-TYPE
            SYNTAX Unsigned32 (0..600)
            MAX-ACCESS read-write
            STATUS current
            DESCRIPTION
                "Interval of module delayed start of DCDC 24V Group. Value range: 0 to 600, unit: s, and the value is accurate to zero decimal place (1)."
            ::= { hwDCDC24VGroupSetEntry 5 }

        hwDCDC24VGroupDefaultOutputVoltage OBJECT-TYPE
            SYNTAX Unsigned32 (240..300)
            MAX-ACCESS read-write
            STATUS current
            DESCRIPTION
                "Default output voltage of DCDC 24V Group. Value range: 24.0 to 30.0, unit: V, and the value is accurate to zero decimal place (.1)."
            ::= { hwDCDC24VGroupSetEntry 6 }

        hwDCDC24VEquip OBJECT IDENTIFIER ::= { hwSiteDCDC24V 2 }

        hwDCDC24VEquipSampTable OBJECT-TYPE
            SYNTAX SEQUENCE OF HwDCDC24VEquipSampEntry
            MAX-ACCESS not-accessible
             STATUS current
             DESCRIPTION
                "/"
            ::= { hwDCDC24VEquip 1 }

        hwDCDC24VEquipSampEntry OBJECT-TYPE
                        SYNTAX HwDCDC24VEquipSampEntry
            MAX-ACCESS not-accessible
             STATUS current
             DESCRIPTION
                "/"
            INDEX { hwDCDC24VEquipID }
            ::= { hwDCDC24VEquipSampTable 1 }

        HwDCDC24VEquipSampEntry            ::= SEQUENCE {
                hwDCDC24VEquipID
                    Unsigned32,
                hwDCDC24VEquipName
                    OCTET STRING,
                hwDCDC24VEquipSequence
                    Unsigned32,
                hwDCDC24VEquipTotalRunTime
                    Unsigned32,
                hwDCDC24VEquipOutputVoltage
                    Unsigned32,
                hwDCDC24VEquipRealOutputCurrent
                    Unsigned32,
                hwDCDC24VEquipDCOutputPower
                    Unsigned32,
                hwDCDC24VEquipModuleOnOffState
                    INTEGER,
                hwDCDC24VEquipHardwareVersion
                    OCTET STRING,
                hwDCDC24VEquipSoftVer
                    OCTET STRING,
                hwDCDC24VEquipAirIntakeTemperature
                    Integer32
            }

        hwDCDC24VEquipID OBJECT-TYPE
            SYNTAX Unsigned32
            MAX-ACCESS read-only
            STATUS current
            DESCRIPTION
                "Equip ID of DCDC 24V. Value range: 0 to 4294967295, unit: NA, and the value is accurate to zero decimal place (1.)."
            ::= { hwDCDC24VEquipSampEntry 1 }

        hwDCDC24VEquipName OBJECT-TYPE
            SYNTAX OCTET STRING (SIZE (0..63))
            MAX-ACCESS read-only
            STATUS current
            DESCRIPTION
                "Equip name of DCDC 24V. Value range: 0 to 63, unit: NA, and the value is accurate to zero decimal place (1.)."
            ::= { hwDCDC24VEquipSampEntry 2 }

        hwDCDC24VEquipSequence OBJECT-TYPE
            SYNTAX Unsigned32 (0..127)
            MAX-ACCESS read-only
            STATUS current
            DESCRIPTION
                "sequence number of DCDC 24V. Value range: 0 to 127, unit: NA, and the value is accurate to zero decimal place (1.)."
            ::= { hwDCDC24VEquipSampEntry 3 }

        hwDCDC24VEquipTotalRunTime OBJECT-TYPE
            SYNTAX Unsigned32 (0..876000)
            MAX-ACCESS read-only
            STATUS current
            DESCRIPTION
                "Total run time of DCDC 24V. Value range: 0 to 876000, unit: h, and the value is accurate to zero decimal place (1.)."
            ::= { hwDCDC24VEquipSampEntry 4 }

        hwDCDC24VEquipOutputVoltage OBJECT-TYPE
            SYNTAX Unsigned32 (0..480)
            MAX-ACCESS read-only
            STATUS current
            DESCRIPTION
                "Total output voltage of DCDC 24V. Value range: 0 to 480, unit: V, and the value is accurate to zero decimal place (.1)."
            ::= { hwDCDC24VEquipSampEntry 5 }

        hwDCDC24VEquipRealOutputCurrent OBJECT-TYPE
            SYNTAX Unsigned32 (0..100000)
            MAX-ACCESS read-only
            STATUS current
            DESCRIPTION
                "Total output current of DCDC 24V. Value range: 0 to 100000, unit: A, and the value is accurate to zero decimal place (.1)."
            ::= { hwDCDC24VEquipSampEntry 6 }

        hwDCDC24VEquipDCOutputPower OBJECT-TYPE
            SYNTAX Unsigned32 (0..300000)
            MAX-ACCESS read-only
            STATUS current
            DESCRIPTION
                "Total output power of DCDC 24V. Value range: 0 to 300000, unit: W, and the value is accurate to zero decimal place (.1)."
            ::= { hwDCDC24VEquipSampEntry 7 }

        hwDCDC24VEquipModuleOnOffState OBJECT-TYPE
            SYNTAX INTEGER
                {
                on(1),
                off(2),
                unknown(255)
                }
            MAX-ACCESS read-only
            STATUS current
            DESCRIPTION
                "Equipment module on/off state of DCDC 24V, It is an enumeration type:
                If the enumeration value is 1, it indicates that the module is on;
                If the enumeration value is 2, it indicates that the module is off;"
            ::= { hwDCDC24VEquipSampEntry 8 }

        hwDCDC24VEquipHardwareVersion OBJECT-TYPE
            SYNTAX OCTET STRING (SIZE (0..63))
            MAX-ACCESS read-only
            STATUS current
            DESCRIPTION
                "DCDC 24V Equip Hardware Version"
            ::= { hwDCDC24VEquipSampEntry 9 }

        hwDCDC24VEquipSoftVer OBJECT-TYPE
            SYNTAX OCTET STRING (SIZE (0..63))
            MAX-ACCESS read-only
            STATUS current
            DESCRIPTION
                "DCDC 24V Equip Soft Version"
            ::= { hwDCDC24VEquipSampEntry 10 }

        hwDCDC24VEquipAirIntakeTemperature OBJECT-TYPE
            SYNTAX Integer32 (-300..300)
            MAX-ACCESS read-only
            STATUS current
            DESCRIPTION
                "Intake temperature of DCDC 24V Equipment. Value range: -300 to 300, unit: degC, and the value is an integer (1)."
            ::= { hwDCDC24VEquipSampEntry 11 }

        hwPVAdapterGroup OBJECT IDENTIFIER ::= { hwSiteMonitorMIBObjects 53 }

        hwPVAdapterGroupSampTable OBJECT-TYPE
            SYNTAX SEQUENCE OF HwPVAdapterGroupSampEntry
            MAX-ACCESS not-accessible
             STATUS current
             DESCRIPTION
                ""
            ::= { hwPVAdapterGroup 1 }

        hwPVAdapterGroupSampEntry OBJECT-TYPE
                        SYNTAX HwPVAdapterGroupSampEntry
            MAX-ACCESS not-accessible
             STATUS current
             DESCRIPTION
                ""
            INDEX { hwPVAdapterGroupIndex }
            ::= { hwPVAdapterGroupSampTable 1 }

        HwPVAdapterGroupSampEntry            ::= SEQUENCE {
                hwPVAdapterGroupIndex
                    Unsigned32,
                hwPVAdapterGroupEquipId
                    Unsigned32,
                hwPVAdapterGroupEquipName
                    OCTET STRING,
                hwPVAdapterGroupTotalOutCurr
                    Unsigned32,
                hwPVAdapterGroupTotalOutPower
                    Unsigned32,
                hwPVAdapterGroupTotalInKW
                    Unsigned32,
                hwPVAdapterGroupTotalOutKW
                    Unsigned32,
                hwPVAdapterGroupFoundNum
                    Unsigned32,
                hwPVAdapterGroupLocateStatus
                    INTEGER,
                hwPVAdapterGroupRunStatus
                    INTEGER,
                hwPVAdapterGroupCommFaultNum
                    Unsigned32,
                hwPVAdapterGroupCurrentHourlyOutputPower
                    Unsigned32,
                hwPVAdapterGroupCurrentDayOutputPower
                    Unsigned32,
                hwPVAdapterGroupCurrentWeeklyOutputPower
                    Unsigned32,
                hwPVAdapterGroupCurrentMonthlyOutputPower
                    Unsigned32,
                hwPVAdapterGroupCurrentYearlyOutputPower
                    Unsigned32,
                hwPVAdapterGroupPVGroupLockEnableState
                    INTEGER
            }

        hwPVAdapterGroupIndex OBJECT-TYPE
            SYNTAX Unsigned32
            MAX-ACCESS read-only
            STATUS current
            DESCRIPTION
                "PV Adapter group table index. Lines of the device list are restricted by the quantity of PV Adapter group."
            ::= { hwPVAdapterGroupSampEntry 1 }

        hwPVAdapterGroupEquipId OBJECT-TYPE
            SYNTAX Unsigned32
            MAX-ACCESS read-only
            STATUS current
            DESCRIPTION
                "PV Adapter group device ID."
            ::= { hwPVAdapterGroupSampEntry 2 }

        hwPVAdapterGroupEquipName OBJECT-TYPE
            SYNTAX OCTET STRING (SIZE (0..63))
            MAX-ACCESS read-only
            STATUS current
            DESCRIPTION
                "PV Adapter group name, of the character string type, is used to specify PV Adapter group.
                
                "
            ::= { hwPVAdapterGroupSampEntry 3 }

        hwPVAdapterGroupTotalOutCurr OBJECT-TYPE
            SYNTAX Unsigned32 (0..240000)
            MAX-ACCESS read-only
            STATUS current
            DESCRIPTION
                "PV Adapter group total Output current, Value range: 0.0 to 24000.0.Unit: A.and the value is accurate to one decimal space (.1).  If the value is 2147483647(0x7FFFFFFF), it indicates that the value is invalid."
            ::= { hwPVAdapterGroupSampEntry 4 }

        hwPVAdapterGroupTotalOutPower OBJECT-TYPE
            SYNTAX Unsigned32 (0..4294967295)
            MAX-ACCESS read-only
            STATUS current
            DESCRIPTION
                "The PV Adapter group total output power; 
                Value range: 0 to 4294967295, 
                and the value is accurate to two decimal place (.01), 
                If the value is 2147483647(0x7FFFFFFF), it indicates that the value is invalid."
            ::= { hwPVAdapterGroupSampEntry 5 }

        hwPVAdapterGroupTotalInKW OBJECT-TYPE
            SYNTAX Unsigned32 (0..10000000)
            MAX-ACCESS read-only
            STATUS current
            DESCRIPTION
                "Total input power of the  PV Adapter group. Value range: 0 to 100000, unit: kW, and the value is accurate to two decimal place (.01). If the value is 2147483647(0x7FFFFFFF), it indicates that the value is invalid."
            ::= { hwPVAdapterGroupSampEntry 6 }

        hwPVAdapterGroupTotalOutKW OBJECT-TYPE
            SYNTAX Unsigned32 (0..10000000)
            MAX-ACCESS read-only
            STATUS current
            DESCRIPTION
                "Total output power of the PV Adapter group. Value range: 0 to 100000, unit: kW, and the value is accurate to two decimal place (.01). If the value is 2147483647(0x7FFFFFFF), it indicates that the value is invalid."
            ::= { hwPVAdapterGroupSampEntry 7 }

        hwPVAdapterGroupFoundNum OBJECT-TYPE
            SYNTAX Unsigned32 (0..100)
            MAX-ACCESS read-only
            STATUS current
            DESCRIPTION
                "The found number in the PV Adapter group; 
                Value range: 0 to 100.   
                If the value is 2147483647(0x7FFFFFFF), it indicates that the value is invalid."
            ::= { hwPVAdapterGroupSampEntry 8 }

        hwPVAdapterGroupLocateStatus OBJECT-TYPE
            SYNTAX INTEGER
                {
                positioningSuccess(1),
                positioningFailed(2),
                notPosition(3),
                positioning(4),
                unknown(255)
                }
            MAX-ACCESS read-only
            STATUS current
            DESCRIPTION
                "Locate states of the PV Adapter group. It is an enumeration type: 
                  If the enumeration value is 1, it indicates that the PV Adapter positioning success;
                  If the enumeration value is 2, it indicates that the PV Adapter positioning failed.
                  If the enumeration value is 3, it indicates that the PV Adapter not position;
                  If the enumeration value is 4, it indicates that the PV Adapter is positioning;
                  If the enumeration value is 255, it indicates that the PV Adapter is in the unknown state."
            ::= { hwPVAdapterGroupSampEntry 9 }

        hwPVAdapterGroupRunStatus OBJECT-TYPE
            SYNTAX INTEGER
                {
                off(1),
                on(2),
                unknown(255)
                }
            MAX-ACCESS read-only
            STATUS current
            DESCRIPTION
                "Run states of the PV Adapter group. It is an enumeration type: 
                  If the enumeration value is 1, it indicates that the PV Adapter is off;
                  If the enumeration value is 2, it indicates that the PV Adapter is on;
                  If the enumeration value is 255, it indicates that the PV Adapter is in the unknown state."
            ::= { hwPVAdapterGroupSampEntry 10 }

        hwPVAdapterGroupCommFaultNum OBJECT-TYPE
            SYNTAX Unsigned32 (0..100)
            MAX-ACCESS read-only
            STATUS current
            DESCRIPTION
                "The communication failed found number in the PV Adapter group; 
                Value range: 0 to 100.   
                If the value is 2147483647(0x7FFFFFFF), it indicates that the value is invalid."
            ::= { hwPVAdapterGroupSampEntry 11 }

        hwPVAdapterGroupCurrentHourlyOutputPower OBJECT-TYPE
            SYNTAX Unsigned32 (0..4294967295)
            MAX-ACCESS read-only
            STATUS current
            DESCRIPTION
                "The PV Optimizer group current hourly output power; 
                Value range: 0 to 4294967295, 
                and the value is accurate to two decimal place (.01)."
            ::= { hwPVAdapterGroupSampEntry 12 }

        hwPVAdapterGroupCurrentDayOutputPower OBJECT-TYPE
            SYNTAX Unsigned32 (0..4294967295)
            MAX-ACCESS read-only
            STATUS current
            DESCRIPTION
                "The PV Optimizer group current-day output power; 
                Value range: 0 to 4294967295, 
                and the value is accurate to two decimal place (.01)."
            ::= { hwPVAdapterGroupSampEntry 13 }

        hwPVAdapterGroupCurrentWeeklyOutputPower OBJECT-TYPE
            SYNTAX Unsigned32 (0..4294967295)
            MAX-ACCESS read-only
            STATUS current
            DESCRIPTION
                "The PV Optimizer group current weekly output power; 
                Value range: 0 to 4294967295, 
                and the value is accurate to two decimal place (.01)."
            ::= { hwPVAdapterGroupSampEntry 14 }

        hwPVAdapterGroupCurrentMonthlyOutputPower OBJECT-TYPE
            SYNTAX Unsigned32 (0..4294967295)
            MAX-ACCESS read-only
            STATUS current
            DESCRIPTION
                "The PV Optimizer group current monthly output power; 
                Value range: 0 to 4294967295, 
                and the value is accurate to two decimal place (.01)."
            ::= { hwPVAdapterGroupSampEntry 15 }

        hwPVAdapterGroupCurrentYearlyOutputPower OBJECT-TYPE
            SYNTAX Unsigned32 (0..4294967295)
            MAX-ACCESS read-only
            STATUS current
            DESCRIPTION
                "The PV Optimizer group current yearly output power; 
                Value range: 0 to 4294967295, 
                and the value is accurate to two decimal place (.01)."
            ::= { hwPVAdapterGroupSampEntry 16 }

        hwPVAdapterGroupPVGroupLockEnableState OBJECT-TYPE
            SYNTAX INTEGER
                {
                lockFunctionFullyClosed(1), lockFunctionFullyOpen(2), partialLockFunctionOpen(3)
                }
            MAX-ACCESS read-only
            STATUS current
            DESCRIPTION
                "PV Group Lock Enable State of the PV Adapter group. Only present on photovoltaic adapters, hybrid PV anti-theft requirements. It is an enumeration type: 
                  If the enumeration value is 1, it indicates that the LockFunctionFullyClosed;
                  If the enumeration value is 2, it indicates that the LockFunctionFullyOpen;
                  If the enumeration value is 3, it indicates that the PartialLockFunctionOpen."
            ::= { hwPVAdapterGroupSampEntry 17 }

        hwPVAdapterSampTable OBJECT-TYPE
            SYNTAX SEQUENCE OF HwPVAdapterSampEntry
            MAX-ACCESS not-accessible
             STATUS current
             DESCRIPTION
                ""
            ::= { hwPVAdapterGroup 2 }

        hwPVAdapterSampEntry OBJECT-TYPE
                        SYNTAX HwPVAdapterSampEntry
            MAX-ACCESS not-accessible
             STATUS current
             DESCRIPTION
                ""
            INDEX { hwPVAdapterIndex }
            ::= { hwPVAdapterSampTable 1 }

        HwPVAdapterSampEntry            ::= SEQUENCE {
                hwPVAdapterIndex
                    Unsigned32,
                hwPVAdapterEquipId
                    Unsigned32,
                hwPVAdapterEquipName
                    OCTET STRING,
                hwPVAdapterInputVoltage
                    Unsigned32,
                hwPVAdapterOutputVoltage
                    Unsigned32,
                hwPVAdapterOutputCurrent
                    Unsigned32,
                hwPVAdapterModuleAddress
                    Unsigned32,
                hwPVAdapterPowerOnOffStatus
                    INTEGER,
                hwPVAdapterSoftwareVersion
                    OCTET STRING,
                hwPVAdapterHardwareVersion
                    OCTET STRING,
                hwPVAdapterInputCurrent
                    Unsigned32,
                hwPVAdapterTemperature
                    Integer32,
                hwPVAdapterStringNumber
                    Unsigned32,
                hwPVAdapterBarcode
                    OCTET STRING,
                hwPVAdapterPVLockEnableState
                    INTEGER,
                hwPVAdapterSTASoftwareVersion
                    OCTET STRING,
                hwPVAdapterOutputPower
                    Unsigned32,
                hwPVAdapterType
                    OCTET STRING,
                hwPVAdapterPCUSlot
                    Unsigned32,
                hwPVAdapterSSUSlot
                    Unsigned32
            }

        hwPVAdapterIndex OBJECT-TYPE
            SYNTAX Unsigned32
            MAX-ACCESS read-only
            STATUS current
            DESCRIPTION
                "PV Adapter table index. Lines of the device list are restricted by the quantity of PV Adapter group."
            ::= { hwPVAdapterSampEntry 1 }

        hwPVAdapterEquipId OBJECT-TYPE
            SYNTAX Unsigned32
            MAX-ACCESS read-only
            STATUS current
            DESCRIPTION
                "PV Adapter  device ID."
            ::= { hwPVAdapterSampEntry 2 }

        hwPVAdapterEquipName OBJECT-TYPE
            SYNTAX OCTET STRING (SIZE (0..63))
            MAX-ACCESS read-only
            STATUS current
            DESCRIPTION
                "PV Adapter  name, of the character string type, is used to specify PV Adapter .
                
                "
            ::= { hwPVAdapterSampEntry 3 }

        hwPVAdapterInputVoltage OBJECT-TYPE
            SYNTAX Unsigned32 (0..5000)
            MAX-ACCESS read-only
            STATUS current
            DESCRIPTION
                "PV Adapter Input Voltage.
                Value range: 0.0 to 500.0, 
                resolution: 2V, 
                unit: V,
                and the value is accurate to one decimal place (.1), 
                If the value is 2147483647(0x7FFFFFFF), it indicates that the value is invalid."
            ::= { hwPVAdapterSampEntry 4 }

        hwPVAdapterOutputVoltage OBJECT-TYPE
            SYNTAX Unsigned32 (0..2000)
            MAX-ACCESS read-only
            STATUS current
            DESCRIPTION
                "PV Adapter Output Voltage.
                Value range: 0.0 to 200.0, 
                resolution: 1V, 
                unit: V,
                and the value is accurate to one decimal place (.1), 
                If the value is 2147483647(0x7FFFFFFF), it indicates that the value is invalid."
            ::= { hwPVAdapterSampEntry 5 }

        hwPVAdapterOutputCurrent OBJECT-TYPE
            SYNTAX Unsigned32 (0..10000)
            MAX-ACCESS read-only
            STATUS current
            DESCRIPTION
                "PV Adapter Output Current.
                Value range: 0 to 1000,   
                resolution: 0.5A, 
                unit: A,
                and the value is accurate to one decimal place (.1), 
                If the value is 2147483647(0x7FFFFFFF), it indicates that the value is invalid."
            ::= { hwPVAdapterSampEntry 6 }

        hwPVAdapterModuleAddress OBJECT-TYPE
            SYNTAX Unsigned32 (0..127)
            MAX-ACCESS read-only
            STATUS current
            DESCRIPTION
                "PV Adapter Module Address.
                Value range: 0 to 127.   
                If the value is 2147483647(0x7FFFFFFF), it indicates that the value is invalid."
            ::= { hwPVAdapterSampEntry 7 }

        hwPVAdapterPowerOnOffStatus OBJECT-TYPE
            SYNTAX INTEGER
                {
                powerOn(1), powerOff(2) 
                }
            MAX-ACCESS read-only
            STATUS current
            DESCRIPTION
                "PV Adapter On/Off Status. It is an enumeration type:  
                  If the enumeration value is 1, it indicates that the powerOn;
                  If the enumeration value is 2, it indicates that the powerOff."
            ::= { hwPVAdapterSampEntry 8 }

        hwPVAdapterSoftwareVersion OBJECT-TYPE
            SYNTAX OCTET STRING
            MAX-ACCESS read-only
            STATUS current
            DESCRIPTION
                "PV Adapter Software Version, of the character string type. Signal value length is 5."
            ::= { hwPVAdapterSampEntry 9 }

        hwPVAdapterHardwareVersion OBJECT-TYPE
            SYNTAX OCTET STRING
            MAX-ACCESS read-only
            STATUS current
            DESCRIPTION
                "PV Adapter Hardware Version, of the character string type. Signal value length is 5."
            ::= { hwPVAdapterSampEntry 10 }

        hwPVAdapterInputCurrent OBJECT-TYPE
            SYNTAX Unsigned32 (0..1270)
            MAX-ACCESS read-only
            STATUS current
            DESCRIPTION
                "PV Adapter Input Current. Only present on photovoltaic adapters.
                Value range: 0 to 127.   
                resolution: 1A, 
                unit: A,
                and the value is accurate to one decimal place (.1), 
                If the value is 2147483647(0x7FFFFFFF), it indicates that the value is invalid."
            ::= { hwPVAdapterSampEntry 11 }

        hwPVAdapterTemperature OBJECT-TYPE
            SYNTAX Integer32 (-300..300)
            MAX-ACCESS read-only
            STATUS current
            DESCRIPTION
                "PV Adapter Temperature. Only present on photovoltaic adapters.
                Value range: -300 to 300, 
                resolution: 1°C, 
                unit: °C,
                If the value is 2147483647(0x7FFFFFFF), it indicates that the value is invalid."
            ::= { hwPVAdapterSampEntry 12 }

        hwPVAdapterStringNumber OBJECT-TYPE
            SYNTAX Unsigned32 (0..255)
            MAX-ACCESS read-only
            STATUS current
            DESCRIPTION
                "PV Adapter String No. Only present on photovoltaic adapters.
                Value range: 0 to 255.   
                If the value is 2147483647(0x7FFFFFFF), it indicates that the value is invalid."
            ::= { hwPVAdapterSampEntry 13 }

        hwPVAdapterBarcode OBJECT-TYPE
            SYNTAX OCTET STRING
            MAX-ACCESS read-only
            STATUS current
            DESCRIPTION
                "PV Adapter Barcode. Signal value length is 25."
            ::= { hwPVAdapterSampEntry 14 }

        hwPVAdapterPVLockEnableState OBJECT-TYPE
            SYNTAX INTEGER
                {
                lockFunctionOff(1), lockFunctionOn(2) 
                }
            MAX-ACCESS read-only
            STATUS current
            DESCRIPTION
                "PV Adapter PV Lock Enable State. Only present on photovoltaic adapters. It is an enumeration type: 
                  If the enumeration value is 1, it indicates that the LockFunctionOff;
                  If the enumeration value is 2, it indicates that the LockFunctionOn."
            ::= { hwPVAdapterSampEntry 15 }

        hwPVAdapterSTASoftwareVersion OBJECT-TYPE
            SYNTAX OCTET STRING
            MAX-ACCESS read-only
            STATUS current
            DESCRIPTION
                "PV Adapter STA Software Version, of the character string type. Only present on photovoltaic adapters. Signal value length is 5."
            ::= { hwPVAdapterSampEntry 16 }

        hwPVAdapterOutputPower OBJECT-TYPE
            SYNTAX Unsigned32 (0..10000000)
            MAX-ACCESS read-only
            STATUS current
            DESCRIPTION
                "PV Adapter Output Power.
                Value range: 0 to 100000, 
                resolution: 0.03kwh, 
                unit: kW,
                and the value is accurate to two decimal place (.01), 
                If the value is 2147483647(0x7FFFFFFF), it indicates that the value is invalid."
            ::= { hwPVAdapterSampEntry 17 }

        hwPVAdapterType OBJECT-TYPE
            SYNTAX OCTET STRING
            MAX-ACCESS read-only
            STATUS current
            DESCRIPTION
                "PV Adapter Type, of the character string type. Only present on photovoltaic adapters. Signal value length is 25."
            ::= { hwPVAdapterSampEntry 18 }

        hwPVAdapterPCUSlot OBJECT-TYPE
            SYNTAX Unsigned32 (1..9)
            MAX-ACCESS read-only
            STATUS current
            DESCRIPTION
                "PV Adapter PCU Slot. Only present on photovoltaic adapters.
                Value range: 1 to 9, 
                resolution: 1, 
                If the value is 2147483647(0x7FFFFFFF), it indicates that the value is invalid."
            ::= { hwPVAdapterSampEntry 19 }

        hwPVAdapterSSUSlot OBJECT-TYPE
            SYNTAX Unsigned32 (1..65535)
            MAX-ACCESS read-only
            STATUS current
            DESCRIPTION
                "PV Adapter SSU Slot. Only present on photovoltaic adapters.
                Value range: 1 to 65535, 
                resolution: 1, 
                If the value is 2147483647(0x7FFFFFFF), it indicates that the value is invalid."
            ::= { hwPVAdapterSampEntry 20 }

        hwSiteTankAbs OBJECT IDENTIFIER ::= { hwSiteMonitorMIBObjects 24 }

        hwSiteTankAbsEquip OBJECT-TYPE
            SYNTAX SEQUENCE OF HwSiteTankAbsEquipEntry
            MAX-ACCESS not-accessible
             STATUS current
             DESCRIPTION
                ""
            ::= { hwSiteTankAbs 1 }

        hwSiteTankAbsEquipEntry OBJECT-TYPE
                        SYNTAX HwSiteTankAbsEquipEntry
            MAX-ACCESS not-accessible
             STATUS current
             DESCRIPTION
                ""
            INDEX { hwTankAbsIndex }
            ::= { hwSiteTankAbsEquip 1 }

        HwSiteTankAbsEquipEntry            ::= SEQUENCE {
                hwTankAbsIndex
                    Unsigned32,
                hwTankAbsEquipId
                    Unsigned32,
                hwTankAbsEquipName
                    OCTET STRING,
                hwRemainingFuelGallon
                    Unsigned32,
                hwFuelLevel
                    Unsigned32,
                hwFuelViscosity
                    Unsigned32,
                hwFuelDensity
                    Unsigned32,
                hwFuelDielectricConstant
                    Unsigned32,
                hwFuelTemperature
                    Integer32
            }

        hwTankAbsIndex OBJECT-TYPE
            SYNTAX Unsigned32
            MAX-ACCESS read-only
            STATUS current
            DESCRIPTION
                "TankAbs table index,which value range:1 to 256. Lines of the device list are restricted by the quantity of TankAbs."
            ::= { hwSiteTankAbsEquipEntry 1 }

        hwTankAbsEquipId OBJECT-TYPE
            SYNTAX Unsigned32
            MAX-ACCESS read-only
            STATUS current
            DESCRIPTION
                "TankAbs device ID. Value range: 027'001 to 027'255, in which the first digits indicate the device type and the last three digits indicate the device SN."
            ::= { hwSiteTankAbsEquipEntry 2 }

        hwTankAbsEquipName OBJECT-TYPE
            SYNTAX OCTET STRING (SIZE (0..63))
            MAX-ACCESS read-only
            STATUS current
            DESCRIPTION
                "Device name of the TankAbs module, character string type, is used to specify the TankAbs module. Otherwise, the configured character can not be any other languages except English."
            ::= { hwSiteTankAbsEquipEntry 3 }

        hwRemainingFuelGallon OBJECT-TYPE
            SYNTAX Unsigned32 (0..10000000)
            MAX-ACCESS read-only
            STATUS current
            DESCRIPTION
                "RemainingFuel.Value range: 0 to 100000, unit: Gal, and the value is two decimal space (.01). If the value is 2147483647(0x7FFFFFFF), it indicates that the value is invalid."
            ::= { hwSiteTankAbsEquipEntry 4 }

        hwFuelLevel OBJECT-TYPE
            SYNTAX Unsigned32 (0..1000)
            MAX-ACCESS read-only
            STATUS current
            DESCRIPTION
                "FuelLevel.Value range: 0 to 1000, unit: cm,  and the value is an integer (.0). If the value is 2147483647(0x7FFFFFFF), it indicates that the value is invalid."
            ::= { hwSiteTankAbsEquipEntry 5 }

        hwFuelViscosity OBJECT-TYPE
            SYNTAX Unsigned32 (50..5000)
            MAX-ACCESS read-only
            STATUS current
            DESCRIPTION
                "FuelViscosity.Value range: 0.5 to 50, unit: mPa-s, and the value is two decimal space (.01). If the value is 2147483647(0x7FFFFFFF), it indicates that the value is invalid."
            ::= { hwSiteTankAbsEquipEntry 6 }

        hwFuelDensity OBJECT-TYPE
            SYNTAX Unsigned32 (650..1500)
            MAX-ACCESS read-only
            STATUS current
            DESCRIPTION
                "FuelDensity.Value range: 0.65 to 1.50, unit: gm/cc, and the value is three decimal space (.001). If the value is 2147483647(0x7FFFFFFF), it indicates that the value is invalid."
            ::= { hwSiteTankAbsEquipEntry 7 }

        hwFuelDielectricConstant OBJECT-TYPE
            SYNTAX Unsigned32 (100..600)
            MAX-ACCESS read-only
            STATUS current
            DESCRIPTION
                "FuelDielectricConstant.Value range: 1 to 6, unit: NA, and the value is two decimal space (.2). If the value is 2147483647(0x7FFFFFFF), it indicates that the value is invalid."
            ::= { hwSiteTankAbsEquipEntry 8 }

        hwFuelTemperature OBJECT-TYPE
            SYNTAX Integer32 (-3000..10000)
            MAX-ACCESS read-only
            STATUS current
            DESCRIPTION
                "FuelTemperature.Value range: -30 to 100, unit: degC, and the value is two decimal space (.01). . If the value is 2147483647(0x7FFFFFFF), it indicates that the value is invalid."
            ::= { hwSiteTankAbsEquipEntry 9 }

        hwNaradaBatt OBJECT IDENTIFIER ::= { hwSiteMonitorMIBObjects 56 }

        hwNaradaBattEquip OBJECT IDENTIFIER ::= { hwNaradaBatt 1 }

        hwNaradaBattEquipSampTable OBJECT-TYPE
            SYNTAX SEQUENCE OF HwNaradaBattEquipSampEntry
            MAX-ACCESS not-accessible
             STATUS current
             DESCRIPTION
                "/"
            ::= { hwNaradaBattEquip 1 }

        hwNaradaBattEquipSampEntry OBJECT-TYPE
                        SYNTAX HwNaradaBattEquipSampEntry
            MAX-ACCESS not-accessible
             STATUS current
             DESCRIPTION
                "/"
            INDEX { hwNaradaBattEquipIndex }
            ::= { hwNaradaBattEquipSampTable 1 }

        HwNaradaBattEquipSampEntry            ::= SEQUENCE {
                hwNaradaBattEquipIndex
                    Unsigned32,
                hwNaradaBattEquipId
                    Unsigned32,
                hwNaradaBattEquipName
                    OCTET STRING,
                hwNaradaBattCommState
                    INTEGER,
                hwNaradaBattConnPort
                    OCTET STRING,
                hwNaradaBattEquipAddr
                    Unsigned32,
                hwNaradaBattVoltOfPack
                    Unsigned32,
                hwNaradaBattCurrent
                    Integer32,
                hwNaradaBattRemainingAH
                    Unsigned32,
                hwNaradaBattAverageCellTemp
                    Integer32,
                hwNaradaBattEnvTemp
                    Integer32,
                hwNaradaBattSOC
                    Unsigned32
            }

        hwNaradaBattEquipIndex OBJECT-TYPE
            SYNTAX Unsigned32
            MAX-ACCESS read-only
            STATUS current
            DESCRIPTION
                "Narada battary table index. Lines of the device list are restricted by the quantity of Narada battary."
            ::= { hwNaradaBattEquipSampEntry 1 }

        hwNaradaBattEquipId OBJECT-TYPE
            SYNTAX Unsigned32
            MAX-ACCESS read-only
            STATUS current
            DESCRIPTION
                "Narada battary device ID."
            ::= { hwNaradaBattEquipSampEntry 2 }

        hwNaradaBattEquipName OBJECT-TYPE
            SYNTAX OCTET STRING (SIZE (0..63))
            MAX-ACCESS read-only
            STATUS current
            DESCRIPTION
                "Equip name of Narada battary. "
            ::= { hwNaradaBattEquipSampEntry 3 }

        hwNaradaBattCommState OBJECT-TYPE
            SYNTAX INTEGER
                {
                normal(1),
                faile(2),
                unknown(255)
                }
            MAX-ACCESS read-only
            STATUS current
            DESCRIPTION
                "Communication state of Narada battary, It is an enumeration type: 
                If the enumeration value is 1, it indicates that the communication state is normal;
                If the enumeration value is 2, it indicates that the communication state is failed;"
            ::= { hwNaradaBattEquipSampEntry 4 }

        hwNaradaBattConnPort OBJECT-TYPE
            SYNTAX OCTET STRING (SIZE (0..63))
            MAX-ACCESS read-only
            STATUS current
            DESCRIPTION
                "Connected port of Narada battary. "
            ::= { hwNaradaBattEquipSampEntry 5 }

        hwNaradaBattEquipAddr OBJECT-TYPE
            SYNTAX Unsigned32 (1..254)
            MAX-ACCESS read-only
            STATUS current
            DESCRIPTION
                "Equip address of Narada battary. "
            ::= { hwNaradaBattEquipSampEntry 6 }

        hwNaradaBattVoltOfPack OBJECT-TYPE
            SYNTAX Unsigned32 (0..6400)
            MAX-ACCESS read-only
            STATUS current
            DESCRIPTION
                "Voltage of pack. Value range: 0 to 64, unit: V, and the value is accurate to two decimal place (.01)."
            ::= { hwNaradaBattEquipSampEntry 7 }

        hwNaradaBattCurrent OBJECT-TYPE
            SYNTAX Integer32 (-1000..1000)
            MAX-ACCESS read-only
            STATUS current
            DESCRIPTION
                "Current of Narada battary. Value range: -100 to 100, unit: A, and the value is accurate to one decimal place (.1)."
            ::= { hwNaradaBattEquipSampEntry 8 }

        hwNaradaBattRemainingAH OBJECT-TYPE
            SYNTAX Unsigned32 (0..2000)
            MAX-ACCESS read-only
            STATUS current
            DESCRIPTION
                "Remaining AH of Narada battary. Value range: 0.0 to 200.0, unit: AH, and the value is accurate to one decimal place (.1)."
            ::= { hwNaradaBattEquipSampEntry 9 }

        hwNaradaBattAverageCellTemp OBJECT-TYPE
            SYNTAX Integer32 (-400..1200)
            MAX-ACCESS read-only
            STATUS current
            DESCRIPTION
                "Average cell temperature of Narada battary. Value range: -40 to 120, unit: ℃, and the value is accurate to one decimal place (.1)."
            ::= { hwNaradaBattEquipSampEntry 10 }

        hwNaradaBattEnvTemp OBJECT-TYPE
            SYNTAX Integer32 (-400..1200)
            MAX-ACCESS read-only
            STATUS current
            DESCRIPTION
                "Environment temperature of Narada battary. Value range: -40 to 120, unit: ℃, and the value is accurate to one decimal place (.1)."
            ::= { hwNaradaBattEquipSampEntry 11 }

        hwNaradaBattSOC OBJECT-TYPE
            SYNTAX Unsigned32 (0..10000)
            MAX-ACCESS read-only
            STATUS current
            DESCRIPTION
                "SOC of Narada battary. Value range: 0 to 100, unit: %, and the value is accurate to two decimal place (.01)."
            ::= { hwNaradaBattEquipSampEntry 12 }

        hwMains OBJECT IDENTIFIER ::= { hwSiteMonitorMIBObjects 57 }

        hwMainsEquip OBJECT IDENTIFIER ::= { hwMains 1 }

        hwMainsEquipSampTable OBJECT-TYPE
            SYNTAX SEQUENCE OF HwMainsEquipSampEntry
            MAX-ACCESS not-accessible
             STATUS current
             DESCRIPTION
                "/"
            ::= { hwMainsEquip 1 }

        hwMainsEquipSampEntry OBJECT-TYPE
                        SYNTAX HwMainsEquipSampEntry
            MAX-ACCESS not-accessible
             STATUS current
             DESCRIPTION
                "/"
            INDEX { hwMainsTotalActivePower }
            ::= { hwMainsEquipSampTable 1 }

        HwMainsEquipSampEntry            ::= SEQUENCE {
                hwMainsTotalActivePower
                    Integer32
            }

        hwMainsTotalActivePower OBJECT-TYPE
            SYNTAX Integer32 (0..500000)
            MAX-ACCESS read-only
            STATUS current
            DESCRIPTION
                "Total active power of mains. Value range: 0 to 500000, unit: kW and the value is accurate to two decimal place(.01)."
            ::= { hwMainsEquipSampEntry 1 }

        hwThirdPartyLitBatGroup OBJECT IDENTIFIER ::= { hwSiteMonitorMIBObjects 58 }

        hwThirdPartyLitBatGroupEquip OBJECT IDENTIFIER ::= { hwThirdPartyLitBatGroup 1 }

        hwThirdPartyLitBatGroupSampTable OBJECT-TYPE
            SYNTAX SEQUENCE OF HwThirdPartyLitBatGroupSampEntry
            MAX-ACCESS not-accessible
             STATUS current
             DESCRIPTION
                "/"
            ::= { hwThirdPartyLitBatGroupEquip 1 }

        hwThirdPartyLitBatGroupSampEntry OBJECT-TYPE
                        SYNTAX HwThirdPartyLitBatGroupSampEntry
            MAX-ACCESS not-accessible
             STATUS current
             DESCRIPTION
                "/"
            INDEX { hw3rdPartyBatGrpIndex }
            ::= { hwThirdPartyLitBatGroupSampTable 1 }

        HwThirdPartyLitBatGroupSampEntry            ::= SEQUENCE {
                hw3rdPartyBatGrpIndex
                    Unsigned32,
                hw3rdPartyBatGrpEquipId
                    Unsigned32,
                hw3rdPartyBatGrpEquipName
                    OCTET STRING,
                hw3rdPartyBatGrpVolt
                    Unsigned32,
                hw3rdPartyBatGrpCurr
                    Integer32,
                hw3rdPartyBatGrpStatus
                    INTEGER,
                hw3rdPartyBatGrpSoc
                    Unsigned32,
                hw3rdPartyBatGrpSoh
                    Unsigned32,
                hw3rdPartyBatGrpBatNum
                    Unsigned32
            }

        hw3rdPartyBatGrpIndex OBJECT-TYPE
            SYNTAX Unsigned32
            MAX-ACCESS read-only
            STATUS current
            DESCRIPTION
                "Third-party lithium battary group table index. Lines of the device list are restricted by the quantity of third-party lithium battary group."
            ::= { hwThirdPartyLitBatGroupSampEntry 1 }

        hw3rdPartyBatGrpEquipId OBJECT-TYPE
            SYNTAX Unsigned32
            MAX-ACCESS read-only
            STATUS current
            DESCRIPTION
                "Third-party lithium battary device ID."
            ::= { hwThirdPartyLitBatGroupSampEntry 2 }

        hw3rdPartyBatGrpEquipName OBJECT-TYPE
            SYNTAX OCTET STRING (SIZE (0..63))
            MAX-ACCESS read-only
            STATUS current
            DESCRIPTION
                "Third-party lithium battary group equip name. "
            ::= { hwThirdPartyLitBatGroupSampEntry 3 }

        hw3rdPartyBatGrpVolt OBJECT-TYPE
            SYNTAX Unsigned32 (0..3000)
            MAX-ACCESS read-only
            STATUS current
            DESCRIPTION
                "Third-party lithium battery group voltage. 
                Value range: 0 to 300, 
                unit: V"
            ::= { hwThirdPartyLitBatGroupSampEntry 4 }

        hw3rdPartyBatGrpCurr OBJECT-TYPE
            SYNTAX Integer32 (-30000..30000)
            MAX-ACCESS read-only
            STATUS current
            DESCRIPTION
                "Third-party lithium battery group current. 
                Value range: -3000 to 3000, 
                unit: A"
            ::= { hwThirdPartyLitBatGroupSampEntry 5 }

        hw3rdPartyBatGrpStatus OBJECT-TYPE
            SYNTAX INTEGER
                {
                charge(1),
                discharge(2),
                unknown(255)
                }
            MAX-ACCESS read-only
            STATUS current
            DESCRIPTION
                "Third-party lithium battery group status. 
                charge is 0,discharge is 1."
            ::= { hwThirdPartyLitBatGroupSampEntry 6 }

        hw3rdPartyBatGrpSoc OBJECT-TYPE
            SYNTAX Unsigned32 (0..100)
            MAX-ACCESS read-only
            STATUS current
            DESCRIPTION
                "Third-party lithium battery group SOC. Value range: 0 to 100, unit: %"
            ::= { hwThirdPartyLitBatGroupSampEntry 7 }

        hw3rdPartyBatGrpSoh OBJECT-TYPE
            SYNTAX Unsigned32 (0..100)
            MAX-ACCESS read-only
            STATUS current
            DESCRIPTION
                "Third-party lithium battery group SOH. 
                Value range: 0 to 100, 
                unit: %"
            ::= { hwThirdPartyLitBatGroupSampEntry 8 }

        hw3rdPartyBatGrpBatNum OBJECT-TYPE
            SYNTAX Unsigned32 (0..20)
            MAX-ACCESS read-only
            STATUS current
            DESCRIPTION
                "Number of lithium batteries connected to third-party lithium battery group."
            ::= { hwThirdPartyLitBatGroupSampEntry 9 }

        hwThirdPartyLitBat OBJECT IDENTIFIER ::= { hwSiteMonitorMIBObjects 59 }

        hwThirdPartyLitBatEquip OBJECT IDENTIFIER ::= { hwThirdPartyLitBat 1 }

        hwThirdPartyLitBatSampTable OBJECT-TYPE
            SYNTAX SEQUENCE OF HwThirdPartyLitBatSampEntry
            MAX-ACCESS not-accessible
             STATUS current
             DESCRIPTION
                "/"
            ::= { hwThirdPartyLitBatEquip 1 }

        hwThirdPartyLitBatSampEntry OBJECT-TYPE
                        SYNTAX HwThirdPartyLitBatSampEntry
            MAX-ACCESS not-accessible
             STATUS current
             DESCRIPTION
                "/"
            INDEX { hw3rdPartyBatIndex }
            ::= { hwThirdPartyLitBatSampTable 1 }

        HwThirdPartyLitBatSampEntry            ::= SEQUENCE {
                hw3rdPartyBatIndex
                    Unsigned32,
                hw3rdPartyBatEquipId
                    Unsigned32,
                hw3rdPartyBatEquipName
                    OCTET STRING,
                hw3rdPartyBatEquipAddr
                    Unsigned32,
                hw3rdPartyBatVolt
                    Unsigned32,
                hw3rdPartyBatCurr
                    Integer32,
                hw3rdPartyBatStatus
                    INTEGER,
                hw3rdPartyBatChgMosStatus
                    INTEGER,
                hw3rdPartyBatDischgMosStatus
                    INTEGER,
                hw3rdPartyBatCurrLimitStatus
                    INTEGER,
                hw3rdPartyBatSoh
                    Unsigned32,
                hw3rdPartyBatSoc
                    Unsigned32,
                hw3rdPartyBatCapacity
                    Unsigned32,
                hw3rdPartyBatBmsVersion
                    OCTET STRING,
                hw3rdPartyBatRemainingAh
                    Unsigned32,
                hw3rdPartyBatTotalCycleNum
                    Unsigned32,
                hw3rdPartyBatCell1Volt
                    Unsigned32,
                hw3rdPartyBatCell2Volt
                    Unsigned32,
                hw3rdPartyBatCell3Volt
                    Unsigned32,
                hw3rdPartyBatCell4Volt
                    Unsigned32,
                hw3rdPartyBatCell5Volt
                    Unsigned32,
                hw3rdPartyBatCell6Volt
                    Unsigned32,
                hw3rdPartyBatCell7Volt
                    Unsigned32,
                hw3rdPartyBatCell8Volt
                    Unsigned32,
                hw3rdPartyBatCell9Volt
                    Unsigned32,
                hw3rdPartyBatCell10Volt
                    Unsigned32,
                hw3rdPartyBatCell11Volt
                    Unsigned32,
                hw3rdPartyBatCell12Volt
                    Unsigned32,
                hw3rdPartyBatCell13Volt
                    Unsigned32,
                hw3rdPartyBatCell14Volt
                    Unsigned32,
                hw3rdPartyBatCell15Volt
                    Unsigned32,
                hw3rdPartyBatCell16Volt
                    Unsigned32,
                hw3rdPartyBatMaxCellTemp
                    Integer32,
                hw3rdPartyBatMinCellTemp
                    Integer32,
                hw3rdPartyBatCellTemp1
                    Integer32,
                hw3rdPartyBatCellTemp2
                    Integer32,
                hw3rdPartyBatCellTemp3
                    Integer32,
                hw3rdPartyBatCellTemp4
                    Integer32,
                hw3rdPartyBatCellAmbientTemp
                    Integer32,
                hw3rdPartyBatModel
                    OCTET STRING,
                hw3rdPartyBatEsn
                    OCTET STRING,
                hw3rdPartyBatCellAverageTemp
                    Integer32,
                hw3rdPartyBatManufacturer
                    OCTET STRING,
                hw3rdPartyBatHardwareVersion
                    OCTET STRING,
                hw3rdPartyBatPartCode
                    Unsigned32
            }

        hw3rdPartyBatIndex OBJECT-TYPE
            SYNTAX Unsigned32
            MAX-ACCESS read-only
            STATUS current
            DESCRIPTION
                "Third-party lithium battery table index. Lines of the device list are restricted by the quantity of third-party lithium battery."
            ::= { hwThirdPartyLitBatSampEntry 1 }

        hw3rdPartyBatEquipId OBJECT-TYPE
            SYNTAX Unsigned32
            MAX-ACCESS read-only
            STATUS current
            DESCRIPTION
                "Third-party lithium battery device ID."
            ::= { hwThirdPartyLitBatSampEntry 2 }

        hw3rdPartyBatEquipName OBJECT-TYPE
            SYNTAX OCTET STRING (SIZE (0..63))
            MAX-ACCESS read-only
            STATUS current
            DESCRIPTION
                "Equip name of third-party lithium battery."
            ::= { hwThirdPartyLitBatSampEntry 3 }

        hw3rdPartyBatEquipAddr OBJECT-TYPE
            SYNTAX Unsigned32 (0..255)
            MAX-ACCESS read-only
            STATUS current
            DESCRIPTION
                "Third-party lithium battery equip address,lithium battery types include ZTT,ChinaShoto,Coslight. 
                Value range: 0 to 255."
            ::= { hwThirdPartyLitBatSampEntry 4 }

        hw3rdPartyBatVolt OBJECT-TYPE
            SYNTAX Unsigned32 (0..3000)
            MAX-ACCESS read-only
            STATUS current
            DESCRIPTION
                "Third-party lithium battery voltage,lithium battery types include ZTT,ChinaShoto,Coslight. 
                Value range: 0 to 300,unit: V"
            ::= { hwThirdPartyLitBatSampEntry 5 }

        hw3rdPartyBatCurr OBJECT-TYPE
            SYNTAX Integer32 (-30000..30000)
            MAX-ACCESS read-only
            STATUS current
            DESCRIPTION
                "Third-party lithium battery current,lithium battery types include ZTT,ChinaShoto,Coslight. 
                Value range: -3000 to 3000,unit: A"
            ::= { hwThirdPartyLitBatSampEntry 6 }

        hw3rdPartyBatStatus OBJECT-TYPE
            SYNTAX INTEGER
                {
                online(0),
                offline(1),
                hibernating(2),
                open(3),
                charge(4),
                discharge(5),
                standby(6),
                lowPower(7),
                protected(8),
                limitation(9),
                forbiddenCharge(10),
                regulatedCharge(11),
                float(12),
                nominal(13),
                safe(14),
                idle(15),
                fullyCharged(16),
                moduleFailureButInOperation(17),
                moduleOutOfOperation(18),
                chargeOnline(19),
                unknown(255)
                }
            MAX-ACCESS read-only
            STATUS current
            DESCRIPTION
                "Third-party lithium battery status,lithium battery types include ZTT,ChinaShoto,Coslight. 
                Online is 0, offline is 1, hibernating is 2, open is 3, charge is 4, discharge is 5, standby is 6, lowPower is 7, protected is 8, limitation is 9, forbiddenCharge is 10, regulatedCharge is 11, float is 12, nominal is 13, safe is 14, idle is 15, fullyCharged is 16, moduleFailureButInOperation is 17, moduleOutOfOperation is 18, chargeOnline is 19."
            ::= { hwThirdPartyLitBatSampEntry 7 }

        hw3rdPartyBatChgMosStatus OBJECT-TYPE
            SYNTAX INTEGER
                {
                close(1),
                open(2),
                unknown(255)
                }
            MAX-ACCESS read-only
            STATUS current
            DESCRIPTION
                "Third-party lithium battery charge MOS status,lithium battery types include ZTT. 
                Value range: close is 1, open is 2."
            ::= { hwThirdPartyLitBatSampEntry 8 }

        hw3rdPartyBatDischgMosStatus OBJECT-TYPE
            SYNTAX INTEGER
                {
                close(1),
                open(2),
                unknown(255)
                }
            MAX-ACCESS read-only
            STATUS current
            DESCRIPTION
                "Third-party lithium battery discharge MOS status,lithium battery types include ZTT. 
                Value range: close is 1, open is 2."
            ::= { hwThirdPartyLitBatSampEntry 9 }

        hw3rdPartyBatCurrLimitStatus OBJECT-TYPE
            SYNTAX INTEGER
                {
                limitCurrent(1),
                currentNotLimited(2),
                unknown(255)
                }
            MAX-ACCESS read-only
            STATUS current
            DESCRIPTION
                "Third-party lithium battery current limiting status,lithium battery types include ZTT. 
                Value range: limit current is 1,current not limited is 2, ."
            ::= { hwThirdPartyLitBatSampEntry 10 }

        hw3rdPartyBatSoh OBJECT-TYPE
            SYNTAX Unsigned32 (0..100)
            MAX-ACCESS read-only
            STATUS current
            DESCRIPTION
                "Third-party lithium battery soh,lithium battery types include ZTT,ChinaShoto,Coslight. 
                Value range: 0 to 100,unit: %"
            ::= { hwThirdPartyLitBatSampEntry 11 }

        hw3rdPartyBatSoc OBJECT-TYPE
            SYNTAX Unsigned32 (0..100)
            MAX-ACCESS read-only
            STATUS current
            DESCRIPTION
                "Third-party lithium battery soc,lithium battery types include ZTT,ChinaShoto,Coslight. 
                Value range: 0 to 100,unit: %"
            ::= { hwThirdPartyLitBatSampEntry 12 }

        hw3rdPartyBatCapacity OBJECT-TYPE
            SYNTAX Unsigned32 (0..1000)
            MAX-ACCESS read-only
            STATUS current
            DESCRIPTION
                "Third-party lithium battery capacity,lithium battery types include ZTT,ChinaShoto,Coslight. 
                Value range: 0 to 1000,unit: Ah"
            ::= { hwThirdPartyLitBatSampEntry 13 }

        hw3rdPartyBatBmsVersion OBJECT-TYPE
            SYNTAX OCTET STRING (SIZE (0..100))
            MAX-ACCESS read-only
            STATUS current
            DESCRIPTION
                "Third-party lithium battery bms version,lithium battery types include ZTT."
            ::= { hwThirdPartyLitBatSampEntry 14 }

        hw3rdPartyBatRemainingAh OBJECT-TYPE
            SYNTAX Unsigned32 (0..1000)
            MAX-ACCESS read-only
            STATUS current
            DESCRIPTION
                "Third-party lithium battery remaining capacity,lithium battery types include ZTT,ChinaShoto,Coslight. 
                Value range: 0 to 1000,unit: Ah"
            ::= { hwThirdPartyLitBatSampEntry 15 }

        hw3rdPartyBatTotalCycleNum OBJECT-TYPE
            SYNTAX Unsigned32 (0..3000000)
            MAX-ACCESS read-only
            STATUS current
            DESCRIPTION
                "Third-party lithium battery accumulated number of cycles,lithium battery types include ZTT,ChinaShoto. 
                Value range: 0 to 3000000."
            ::= { hwThirdPartyLitBatSampEntry 16 }

        hw3rdPartyBatCell1Volt OBJECT-TYPE
            SYNTAX Unsigned32 (0..500)
            MAX-ACCESS read-only
            STATUS current
            DESCRIPTION
                "Third-party lithium battery cell 1 voltage,lithium battery types include ZTT,ChinaShoto,Coslight. 
                Value range: 0 to 5,unit: V"
            ::= { hwThirdPartyLitBatSampEntry 17 }

        hw3rdPartyBatCell2Volt OBJECT-TYPE
            SYNTAX Unsigned32 (0..500)
            MAX-ACCESS read-only
            STATUS current
            DESCRIPTION
                "Third-party lithium battery cell 2 voltage,lithium battery types include ZTT,ChinaShoto,Coslight. 
                Value range: 0 to 5,unit: V"
            ::= { hwThirdPartyLitBatSampEntry 18 }

        hw3rdPartyBatCell3Volt OBJECT-TYPE
            SYNTAX Unsigned32 (0..500)
            MAX-ACCESS read-only
            STATUS current
            DESCRIPTION
                "Third-party lithium battery cell 3 voltage,lithium battery types include ZTT,ChinaShoto,Coslight. 
                Value range: 0 to 5,unit: V"
            ::= { hwThirdPartyLitBatSampEntry 19 }

        hw3rdPartyBatCell4Volt OBJECT-TYPE
            SYNTAX Unsigned32 (0..500)
            MAX-ACCESS read-only
            STATUS current
            DESCRIPTION
                "Third-party lithium battery cell 4 voltage,lithium battery types include ZTT,ChinaShoto,Coslight. 
                Value range: 0 to 5,unit: V"
            ::= { hwThirdPartyLitBatSampEntry 20 }

        hw3rdPartyBatCell5Volt OBJECT-TYPE
            SYNTAX Unsigned32 (0..500)
            MAX-ACCESS read-only
            STATUS current
            DESCRIPTION
                "Third-party lithium battery cell 5 voltage,lithium battery types include ZTT,ChinaShoto,Coslight. 
                Value range: 0 to 5,unit: V"
            ::= { hwThirdPartyLitBatSampEntry 21 }

        hw3rdPartyBatCell6Volt OBJECT-TYPE
            SYNTAX Unsigned32 (0..500)
            MAX-ACCESS read-only
            STATUS current
            DESCRIPTION
                "Third-party lithium battery cell 6 voltage,lithium battery types include ZTT,ChinaShoto,Coslight. 
                Value range: 0 to 5,unit: V"
            ::= { hwThirdPartyLitBatSampEntry 22 }

        hw3rdPartyBatCell7Volt OBJECT-TYPE
            SYNTAX Unsigned32 (0..500)
            MAX-ACCESS read-only
            STATUS current
            DESCRIPTION
                "Third-party lithium battery cell 7 voltage,lithium battery types include ZTT,ChinaShoto,Coslight. 
                Value range: 0 to 5,unit: V"
            ::= { hwThirdPartyLitBatSampEntry 23 }

        hw3rdPartyBatCell8Volt OBJECT-TYPE
            SYNTAX Unsigned32 (0..500)
            MAX-ACCESS read-only
            STATUS current
            DESCRIPTION
                "Third-party lithium battery cell 8 voltage,lithium battery types include ztt,shoto,coslight. 
                Value range: 0 to 5,unit: V"
            ::= { hwThirdPartyLitBatSampEntry 24 }

        hw3rdPartyBatCell9Volt OBJECT-TYPE
            SYNTAX Unsigned32 (0..500)
            MAX-ACCESS read-only
            STATUS current
            DESCRIPTION
                "Third-party lithium battery cell 9 voltage,lithium battery types include ZTT,ChinaShoto,Coslight. 
                Value range: 0 to 5,unit: V"
            ::= { hwThirdPartyLitBatSampEntry 25 }

        hw3rdPartyBatCell10Volt OBJECT-TYPE
            SYNTAX Unsigned32 (0..500)
            MAX-ACCESS read-only
            STATUS current
            DESCRIPTION
                "Third-party lithium battery cell 10 voltage,lithium battery types include ZTT,ChinaShoto,Coslight. 
                Value range: 0 to 5,unit: V"
            ::= { hwThirdPartyLitBatSampEntry 26 }

        hw3rdPartyBatCell11Volt OBJECT-TYPE
            SYNTAX Unsigned32 (0..500)
            MAX-ACCESS read-only
            STATUS current
            DESCRIPTION
                "Third-party lithium battery cell 11 voltage,lithium battery types include ZTT,ChinaShoto,Coslight. 
                Value range: 0 to 5,unit: V"
            ::= { hwThirdPartyLitBatSampEntry 27 }

        hw3rdPartyBatCell12Volt OBJECT-TYPE
            SYNTAX Unsigned32 (0..500)
            MAX-ACCESS read-only
            STATUS current
            DESCRIPTION
                "Third-party lithium battery cell 12 voltage,lithium battery types include ZTT,ChinaShoto,Coslight. 
                Value range: 0 to 5,unit: V"
            ::= { hwThirdPartyLitBatSampEntry 28 }

        hw3rdPartyBatCell13Volt OBJECT-TYPE
            SYNTAX Unsigned32 (0..500)
            MAX-ACCESS read-only
            STATUS current
            DESCRIPTION
                "Third-party lithium battery cell 13 voltage,lithium battery types include ZTT,ChinaShoto,Coslight. 
                Value range: 0 to 5,unit: V"
            ::= { hwThirdPartyLitBatSampEntry 29 }

        hw3rdPartyBatCell14Volt OBJECT-TYPE
            SYNTAX Unsigned32 (0..500)
            MAX-ACCESS read-only
            STATUS current
            DESCRIPTION
                "Third-party lithium battery cell 14 voltage,lithium battery types include ZTT,ChinaShoto,Coslight. 
                Value range: 0 to 5,unit: V"
            ::= { hwThirdPartyLitBatSampEntry 30 }

        hw3rdPartyBatCell15Volt OBJECT-TYPE
            SYNTAX Unsigned32 (0..500)
            MAX-ACCESS read-only
            STATUS current
            DESCRIPTION
                "Third-party lithium battery cell 15 voltage,lithium battery types include ZTT,ChinaShoto,Coslight. 
                Value range: 0 to 5,unit: V"
            ::= { hwThirdPartyLitBatSampEntry 31 }

        hw3rdPartyBatCell16Volt OBJECT-TYPE
            SYNTAX Unsigned32 (0..500)
            MAX-ACCESS read-only
            STATUS current
            DESCRIPTION
                "Third-party lithium battery cell 16 voltage,lithium battery types include ZTT,ChinaShoto,Coslight. 
                Value range: 0 to 5,unit: V"
            ::= { hwThirdPartyLitBatSampEntry 32 }

        hw3rdPartyBatMaxCellTemp OBJECT-TYPE
            SYNTAX Integer32 (-50..150)
            MAX-ACCESS read-only
            STATUS current
            DESCRIPTION
                "Third-party lithium battery maximum cell temperature,lithium battery types include ZTT,ChinaShoto,Coslight. 
                Value range: -50 to 150,unit: ℃"
            ::= { hwThirdPartyLitBatSampEntry 33 }

        hw3rdPartyBatMinCellTemp OBJECT-TYPE
            SYNTAX Integer32 (-3000..3000)
            MAX-ACCESS read-only
            STATUS current
            DESCRIPTION
                "Third-party lithium battery minimum cell temperature,lithium battery types include ZTT,ChinaShoto,Coslight. 
                Value range: -3000 to 3000,unit: ℃"
            ::= { hwThirdPartyLitBatSampEntry 34 }

        hw3rdPartyBatCellTemp1 OBJECT-TYPE
            SYNTAX Integer32 (-50..150)
            MAX-ACCESS read-only
            STATUS current
            DESCRIPTION
                "Third-party lithium battery cell temperature 1,lithium battery types include ZTT,ChinaShoto,Coslight. 
                Value range: -50 to 150,unit: ℃"
            ::= { hwThirdPartyLitBatSampEntry 35 }

        hw3rdPartyBatCellTemp2 OBJECT-TYPE
            SYNTAX Integer32 (-50..150)
            MAX-ACCESS read-only
            STATUS current
            DESCRIPTION
                "Lithium battery cell temperature 2,lithium battery types include ZTT,ChinaShoto,Coslight. 
                Value range: -50 to 150,unit: ℃"
            ::= { hwThirdPartyLitBatSampEntry 36 }

        hw3rdPartyBatCellTemp3 OBJECT-TYPE
            SYNTAX Integer32 (-50..150)
            MAX-ACCESS read-only
            STATUS current
            DESCRIPTION
                "Third-party lithium battery cell temperature 3,lithium battery types include ZTT,ChinaShoto,Coslight. 
                Value range: -50 to 150,unit: ℃"
            ::= { hwThirdPartyLitBatSampEntry 37 }

        hw3rdPartyBatCellTemp4 OBJECT-TYPE
            SYNTAX Integer32 (-50..150)
            MAX-ACCESS read-only
            STATUS current
            DESCRIPTION
                "Third-party lithium battery cell temperature 4,lithium battery types include ZTT,ChinaShoto,Coslight. 
                Value range: -50 to 150,unit: ℃"
            ::= { hwThirdPartyLitBatSampEntry 38 }

        hw3rdPartyBatCellAmbientTemp OBJECT-TYPE
            SYNTAX Integer32 (-50..150)
            MAX-ACCESS read-only
            STATUS current
            DESCRIPTION
                "Third-party lithium battery cell ambient temperature,lithium battery types include ZTT,ChinaShoto,Coslight. 
                Value range: -50 to 150,unit: ℃"
            ::= { hwThirdPartyLitBatSampEntry 39 }

        hw3rdPartyBatModel OBJECT-TYPE
            SYNTAX OCTET STRING (SIZE (0..100))
            MAX-ACCESS read-only
            STATUS current
            DESCRIPTION
                "Third-party lithium battery model,lithium battery types include ZTT,ChinaShoto. "
            ::= { hwThirdPartyLitBatSampEntry 40 }

        hw3rdPartyBatEsn OBJECT-TYPE
            SYNTAX OCTET STRING (SIZE (0..100))
            MAX-ACCESS read-only
            STATUS current
            DESCRIPTION
                "Third-party lithium battery ESN,lithium battery types include ZTT,ChinaShoto. "
            ::= { hwThirdPartyLitBatSampEntry 41 }

        hw3rdPartyBatCellAverageTemp OBJECT-TYPE
            SYNTAX Integer32 (-50..150)
            MAX-ACCESS read-only
            STATUS current
            DESCRIPTION
                "Third-party lithiumbattery average cell temperature,lithium battery types include ChinaShoto,Coslight. 
                Value range: -50 to 150,unit: ℃"
            ::= { hwThirdPartyLitBatSampEntry 42 }

        hw3rdPartyBatManufacturer OBJECT-TYPE
            SYNTAX OCTET STRING (SIZE (0..100))
            MAX-ACCESS read-only
            STATUS current
            DESCRIPTION
                "Third-party lithium battery manufacturer,lithium battery types include ChinaShoto. "
            ::= { hwThirdPartyLitBatSampEntry 43 }

        hw3rdPartyBatHardwareVersion OBJECT-TYPE
            SYNTAX OCTET STRING (SIZE (0..100))
            MAX-ACCESS read-only
            STATUS current
            DESCRIPTION
                "Third-party lithium battery hardware version,lithium battery types include ChinaShoto."
            ::= { hwThirdPartyLitBatSampEntry 44 }

        hw3rdPartyBatPartCode OBJECT-TYPE
            SYNTAX Unsigned32 (0..65535)
            MAX-ACCESS read-only
            STATUS current
            DESCRIPTION
                "Third-party lithium battery part code,lithium battery types include Coslight."
            ::= { hwThirdPartyLitBatSampEntry 45 }

        hwThirdPartyAcMeters OBJECT IDENTIFIER ::= { hwSiteMonitorMIBObjects 60 }

        hwThirdPartyAcMeterEquip OBJECT IDENTIFIER ::= { hwThirdPartyAcMeters 1 }

        hwThirdPartyAcMeterSampTable OBJECT-TYPE
            SYNTAX SEQUENCE OF HwThirdPartyAcMeterSampEntry
            MAX-ACCESS not-accessible
             STATUS current
             DESCRIPTION
                "/"
            ::= { hwThirdPartyAcMeterEquip 1 }

        hwThirdPartyAcMeterSampEntry OBJECT-TYPE
                        SYNTAX HwThirdPartyAcMeterSampEntry
            MAX-ACCESS not-accessible
             STATUS current
             DESCRIPTION
                "/"
            INDEX { hwThirdPartyAcMeterIndex }
            ::= { hwThirdPartyAcMeterSampTable 1 }

        HwThirdPartyAcMeterSampEntry            ::= SEQUENCE {
                hwThirdPartyAcMeterIndex
                    Unsigned32,
                hwThirdPartyAcMeterEquipId
                    Unsigned32,
                hwThirdPartyAcMeterEquipName
                    OCTET STRING,
                hwThirdPartyAcMeterFrequency
                    Unsigned32,
                hwThirdPartyAcMeterPhaseAVoltage
                    Unsigned32,
                hwThirdPartyAcMeterPhaseBVoltage
                    Unsigned32,
                hwThirdPartyAcMeterPhaseCVoltage
                    Unsigned32,
                hwThirdPartyAcMeterPhaseL1Current
                    Unsigned32,
                hwThirdPartyAcMeterPhaseL2Current
                    Unsigned32,
                hwThirdPartyAcMeterPhaseL3Current
                    Unsigned32,
                hwThirdPartyAcMeterAPowerFactor
                    Unsigned32,
                hwThirdPartyAcMeterBPowerFactor
                    Unsigned32,
                hwThirdPartyAcMeterCPowerFactor
                    Unsigned32,
                hwThirdPartyAcMeterPhaseL1ReactivePower
                    Integer32,
                hwThirdPartyAcMeterPhaseL2ReactivePower
                    Integer32,
                hwThirdPartyAcMeterPhaseL3ReactivePower
                    Integer32,
                hwThirdPartyAcMeterTotalReactivePower
                    Integer32,
                hwThirdPartyAcMeterPhaseL1ActivePower
                    Unsigned32,
                hwThirdPartyAcMeterPhaseL2ActivePower
                    Unsigned32,
                hwThirdPartyAcMeterPhaseL3ActivePower
                    Unsigned32,
                hwThirdPartyAcMeterTotalActivePower
                    Unsigned32,
                hwThirdPartyAcMeterPhaseL1ApparentPower
                    Unsigned32,
                hwThirdPartyAcMeterPhaseL2ApparentPower
                    Unsigned32,
                hwThirdPartyAcMeterPhaseL3ApparentPower
                    Unsigned32,
                hwThirdPartyAcMeterTotalApparentPower
                    Unsigned32,
                hwThirdPartyAcMeterExportedReactiveEnergy
                    Unsigned32,
                hwThirdPartyAcMeterImportedReactiveEnergy
                    Unsigned32,
                hwThirdPartyAcMeterTotalReactiveEnergy
                    Unsigned32,
                hwThirdPartyAcMeterExportedActiveEnergy
                    Unsigned32,
                hwThirdPartyAcMeterImportedActiveEnergy
                    Unsigned32,
                hwThirdPartyAcMeterTotalActiveEnergy
                    Unsigned32
            }

        hwThirdPartyAcMeterIndex OBJECT-TYPE
            SYNTAX Unsigned32
            MAX-ACCESS read-only
            STATUS current
            DESCRIPTION
                "Ac Ammeter table index,which value range:4096 to 20479. Lines of the device list are restricted by the quantity of AcAmmeter"
            ::= { hwThirdPartyAcMeterSampEntry 1 }

        hwThirdPartyAcMeterEquipId OBJECT-TYPE
            SYNTAX Unsigned32
            MAX-ACCESS read-only
            STATUS current
            DESCRIPTION
                "Ac Ammeter device ID. Value range: 022'001 to 022'255, in which the first digits indicate the device type and the last three digits indicate the device SN."
            ::= { hwThirdPartyAcMeterSampEntry 2 }

        hwThirdPartyAcMeterEquipName OBJECT-TYPE
            SYNTAX OCTET STRING (SIZE (0..63))
            MAX-ACCESS read-only
            STATUS current
            DESCRIPTION
                "Ac Ammeter name, of the character string type, is used to specify Fans. Users can configure it.
                Otherwise, the configured character can not be any other languages except English."
            ::= { hwThirdPartyAcMeterSampEntry 3 }

        hwThirdPartyAcMeterFrequency OBJECT-TYPE
            SYNTAX Unsigned32 (0..10000)
            MAX-ACCESS read-only
            STATUS current
            DESCRIPTION
                "Ac Ammeter frequency, 
                Value range: 0.00 to 100.00.
                Unit: Hz.
                and the value is accurate to two decimal space (.01). 
                If the value is 2147483647(0x7FFFFFFF), it indicates that the value is invalid."
            ::= { hwThirdPartyAcMeterSampEntry 4 }

        hwThirdPartyAcMeterPhaseAVoltage OBJECT-TYPE
            SYNTAX Unsigned32 (0..8000)
            MAX-ACCESS read-only
            STATUS current
            DESCRIPTION
                "Ac Ammeter phase a voltage. It is a real-time analog parameter. 
                Value range: 0.0 to 800.0, 
                unit: V, 
                the value is accurate to one decimal place (.1). 
                If the value is 2147483647(0x7FFFFFFF), it indicates that the value is invalid. "
            ::= { hwThirdPartyAcMeterSampEntry 5 }

        hwThirdPartyAcMeterPhaseBVoltage OBJECT-TYPE
            SYNTAX Unsigned32 (0..8000)
            MAX-ACCESS read-only
            STATUS current
            DESCRIPTION
                "Ac Ammeter phase b voltage. It is a real-time analog parameter. 
                Value range: 0.0 to 800.0, 
                unit: V, 
                the value is accurate to one decimal place (.1). 
                If the value is 2147483647(0x7FFFFFFF), it indicates that the value is invalid. "
            ::= { hwThirdPartyAcMeterSampEntry 6 }

        hwThirdPartyAcMeterPhaseCVoltage OBJECT-TYPE
            SYNTAX Unsigned32 (0..8000)
            MAX-ACCESS read-only
            STATUS current
            DESCRIPTION
                "Ac Ammeter phase c voltage. It is a real-time analog parameter. 
                Value range: 0.0 to 800.0, 
                unit: V, 
                the value is accurate to one decimal place (.1). 
                If the value is 2147483647(0x7FFFFFFF), it indicates that the value is invalid. "
            ::= { hwThirdPartyAcMeterSampEntry 7 }

        hwThirdPartyAcMeterPhaseL1Current OBJECT-TYPE
            SYNTAX Unsigned32 (0..50000)
            MAX-ACCESS read-only
            STATUS current
            DESCRIPTION
                "Ac Ammeter phase a current, 
                Value range: 0.00 to 500.00.
                Unit: A.
                and the value is accurate to two decimal space (.01). 
                If the value is 2147483647(0x7FFFFFFF), it indicates that the value is invalid."
            ::= { hwThirdPartyAcMeterSampEntry 8 }

        hwThirdPartyAcMeterPhaseL2Current OBJECT-TYPE
            SYNTAX Unsigned32 (0..50000)
            MAX-ACCESS read-only
            STATUS current
            DESCRIPTION
                "Ac Ammeter phase b current, 
                Value range: 0.00 to 500.00.
                Unit: A.
                and the value is accurate to two decimal space (.01). 
                If the value is 2147483647(0x7FFFFFFF), it indicates that the value is invalid."
            ::= { hwThirdPartyAcMeterSampEntry 9 }

        hwThirdPartyAcMeterPhaseL3Current OBJECT-TYPE
            SYNTAX Unsigned32 (0..50000)
            MAX-ACCESS read-only
            STATUS current
            DESCRIPTION
                "Ac Ammeter phase c current, 
                Value range: 0.00 to 500.00.
                Unit: A.
                and the value is accurate to two decimal space (.01). 
                If the value is 2147483647(0x7FFFFFFF), it indicates that the value is invalid."
            ::= { hwThirdPartyAcMeterSampEntry 10 }

        hwThirdPartyAcMeterAPowerFactor OBJECT-TYPE
            SYNTAX Unsigned32 (-1000..1000)
            MAX-ACCESS read-only
            STATUS current
            DESCRIPTION
                "Ac Ammeter phase a power factor, 
                Value range: -1.000 to 1.000.
                and the value is accurate to three decimal space (.001). 
                If the value is 2147483647(0x7FFFFFFF), it indicates that the value is invalid."
            ::= { hwThirdPartyAcMeterSampEntry 11 }

        hwThirdPartyAcMeterBPowerFactor OBJECT-TYPE
            SYNTAX Unsigned32 (-1000..1000)
            MAX-ACCESS read-only
            STATUS current
            DESCRIPTION
                "Ac Ammeter phase a power factor, 
                Value range: -1.000 to 1.000.
                and the value is accurate to three decimal space (.001). 
                If the value is 2147483647(0x7FFFFFFF), it indicates that the value is invalid."
            ::= { hwThirdPartyAcMeterSampEntry 12 }

        hwThirdPartyAcMeterCPowerFactor OBJECT-TYPE
            SYNTAX Unsigned32 (-1000..1000)
            MAX-ACCESS read-only
            STATUS current
            DESCRIPTION
                "Ac Ammeter phase a power factor, 
                Value range: -1.000 to 1.000.
                and the value is accurate to three decimal space (.001). 
                If the value is 2147483647(0x7FFFFFFF), it indicates that the value is invalid."
            ::= { hwThirdPartyAcMeterSampEntry 13 }

        hwThirdPartyAcMeterPhaseL1ReactivePower OBJECT-TYPE
            SYNTAX Integer32 (-48000..48000)
            MAX-ACCESS read-only
            STATUS current
            DESCRIPTION
                "The phase L1 Reactive Power; 
                Value range: -480.00 to 480.00, 
                and the value is accurate to two decimal place (.01).
                unit: kvar."
            ::= { hwThirdPartyAcMeterSampEntry 14 }

        hwThirdPartyAcMeterPhaseL2ReactivePower OBJECT-TYPE
            SYNTAX Integer32 (-48000..48000)
            MAX-ACCESS read-only
            STATUS current
            DESCRIPTION
                "The phase L2 Reactive Power; 
                Value range: -480.00 to 480.00, 
                and the value is accurate to two decimal place (.01).
                unit: kvar."
            ::= { hwThirdPartyAcMeterSampEntry 15 }

        hwThirdPartyAcMeterPhaseL3ReactivePower OBJECT-TYPE
            SYNTAX Integer32 (-48000..48000)
            MAX-ACCESS read-only
            STATUS current
            DESCRIPTION
                "The phase L3 Reactive Power; 
                Value range: -480.00 to 480.00, 
                and the value is accurate to two decimal place (.01).
                unit: kvar."
            ::= { hwThirdPartyAcMeterSampEntry 16 }

        hwThirdPartyAcMeterTotalReactivePower OBJECT-TYPE
            SYNTAX Integer32 (-48000..48000)
            MAX-ACCESS read-only
            STATUS current
            DESCRIPTION
                "The Total Reactive Power; 
                Value range: -480.00 to 480.00, 
                and the value is accurate to two decimal place (.01).
                unit: kvar."
            ::= { hwThirdPartyAcMeterSampEntry 17 }

        hwThirdPartyAcMeterPhaseL1ActivePower OBJECT-TYPE
            SYNTAX Unsigned32 (0..48000)
            MAX-ACCESS read-only
            STATUS current
            DESCRIPTION
                "The phase L1 Active Power; 
                Value range: 0.00 to 480.00, 
                and the value is accurate to two decimal place (.01).
                unit: kW."
            ::= { hwThirdPartyAcMeterSampEntry 18 }

        hwThirdPartyAcMeterPhaseL2ActivePower OBJECT-TYPE
            SYNTAX Unsigned32 (0..48000)
            MAX-ACCESS read-only
            STATUS current
            DESCRIPTION
                "The phase L2 Active Power; 
                Value range: 0.00 to 480.00, 
                and the value is accurate to two decimal place (.01).
                unit: kW"
            ::= { hwThirdPartyAcMeterSampEntry 19 }

        hwThirdPartyAcMeterPhaseL3ActivePower OBJECT-TYPE
            SYNTAX Unsigned32 (0..48000)
            MAX-ACCESS read-only
            STATUS current
            DESCRIPTION
                "The phase L3 Active Power; 
                Value range: 0.00 to 480.00, 
                and the value is accurate to two decimal place (.01).
                unit: kW."
            ::= { hwThirdPartyAcMeterSampEntry 20 }

        hwThirdPartyAcMeterTotalActivePower OBJECT-TYPE
            SYNTAX Unsigned32 (0..48000)
            MAX-ACCESS read-only
            STATUS current
            DESCRIPTION
                "Ac Ammeter total active power , Value range: 0.00 to 480.00.Unit: kW.and the value is accurate to two decimal space (.01).  If the value is 2147483647(0x7FFFFFFF), it indicates that the value is invalid."
            ::= { hwThirdPartyAcMeterSampEntry 21 }

        hwThirdPartyAcMeterPhaseL1ApparentPower OBJECT-TYPE
            SYNTAX Unsigned32 (0..48000)
            MAX-ACCESS read-only
            STATUS current
            DESCRIPTION
                "The phase L1 Apparent power. It is a real-time analog parameter. Value range: 0.00 to 480.00, unit: kVA, the value is accurate to two decimal place (.01). If the value is 2147483647(0x7FFFFFFF), it indicates that the value is invalid."
            ::= { hwThirdPartyAcMeterSampEntry 22 }

        hwThirdPartyAcMeterPhaseL2ApparentPower OBJECT-TYPE
            SYNTAX Unsigned32 (0..48000)
            MAX-ACCESS read-only
            STATUS current
            DESCRIPTION
                "The phase L2 Apparent power. It is a real-time analog parameter. Value range: 0.00 to 480.00, unit: kVA, the value is accurate to two decimal place (.01). If the value is 2147483647(0x7FFFFFFF), it indicates that the value is invalid."
            ::= { hwThirdPartyAcMeterSampEntry 23 }

        hwThirdPartyAcMeterPhaseL3ApparentPower OBJECT-TYPE
            SYNTAX Unsigned32 (0..48000)
            MAX-ACCESS read-only
            STATUS current
            DESCRIPTION
                "The phase L3 Apparent power. It is a real-time analog parameter. Value range: 0.00 to 480.00, unit: kVA, the value is accurate to two decimal place (.01). If the value is 2147483647(0x7FFFFFFF), it indicates that the value is invalid."
            ::= { hwThirdPartyAcMeterSampEntry 24 }

        hwThirdPartyAcMeterTotalApparentPower OBJECT-TYPE
            SYNTAX Unsigned32 (0..48000)
            MAX-ACCESS read-only
            STATUS current
            DESCRIPTION
                "The Total Apparent power. It is a real-time analog parameter. Value range: 0.00 to 480.00, unit: kVA, the value is accurate to two decimal place (.01). If the value is 2147483647(0x7FFFFFFF), it indicates that the value is invalid."
            ::= { hwThirdPartyAcMeterSampEntry 25 }

        hwThirdPartyAcMeterExportedReactiveEnergy OBJECT-TYPE
            SYNTAX Unsigned32 (0..100000000000)
            MAX-ACCESS read-only
            STATUS current
            DESCRIPTION
                "AC Exported Reactive Power Consumption. Value range:0.00 to 1000000000.00, resolution 10varh.
                If GET value is 10, it means  the real consumption is 10*10varh = 100varh (0.1kvarh)"
            ::= { hwThirdPartyAcMeterSampEntry 26 }

        hwThirdPartyAcMeterImportedReactiveEnergy OBJECT-TYPE
            SYNTAX Unsigned32 (0..100000000000)
            MAX-ACCESS read-only
            STATUS current
            DESCRIPTION
                "AC Imported Reactive Power Consumption. Value range:0.00 to 1000000000.00, resolution 10varh.
                If GET value is 10, it means  the real consumption is 10*10varh = 100varh (0.1kvarh)"
            ::= { hwThirdPartyAcMeterSampEntry 27 }

        hwThirdPartyAcMeterTotalReactiveEnergy OBJECT-TYPE
            SYNTAX Unsigned32 (0..100000000000)
            MAX-ACCESS read-only
            STATUS current
            DESCRIPTION
                "AC Total Reactive Power Consumption. Value range:0.00 to 1000000000.00, resolution 10varh.
                If GET value is 10, it means  the real consumption is 10*10varh = 100varh (0.1kvarh)"
            ::= { hwThirdPartyAcMeterSampEntry 28 }

        hwThirdPartyAcMeterExportedActiveEnergy OBJECT-TYPE
            SYNTAX Unsigned32 (0..100000000000)
            MAX-ACCESS read-only
            STATUS current
            DESCRIPTION
                "AC Exported Active Power Consumption. Value range:0.00 to 1000000000.00, resolution 10wh."
            ::= { hwThirdPartyAcMeterSampEntry 29 }

        hwThirdPartyAcMeterImportedActiveEnergy OBJECT-TYPE
            SYNTAX Unsigned32 (0..100000000000)
            MAX-ACCESS read-only
            STATUS current
            DESCRIPTION
                "AC Imported Active Power Consumption. Value range:0.00 to 1000000000.00, resolution 10wh."
            ::= { hwThirdPartyAcMeterSampEntry 30 }

        hwThirdPartyAcMeterTotalActiveEnergy OBJECT-TYPE
            SYNTAX Unsigned32 (0..100000000000)
            MAX-ACCESS read-only
            STATUS current
            DESCRIPTION
                "AC Total Active Power Consumption.
                Value range: 0.00 to 1000000000.00
                Unit: kWh.
                and the value is accurate to two decimal space (.01). 
                If the value is 2147483647(0x7FFFFFFF), it indicates that the value is invalid."
            ::= { hwThirdPartyAcMeterSampEntry 31 }

        hwSiteMonitorMIBTraps OBJECT IDENTIFIER ::= { hwSiteMonitorMIB 2 }

        hwSiteAlarmTraps OBJECT IDENTIFIER ::= { hwSiteMonitorMIBTraps 1 }

        hwSiteAlarmTrapsPrefix OBJECT IDENTIFIER ::= { hwSiteAlarmTraps 0 }

        hwRectifierFaultAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "When rectifiers fault alarms happen, a alarm trap will be send. Its correlation binding parameters: Site ID, Site name, Site description, NE ID, Alarm name, Alarm single description, Alarm port description, Alarm severity, and Site alarm SN. 
                Additionally, in order to identify the device, rectifier equipment ID and equipment name are also include in VB(variable bondings)."
            ::= { hwSiteAlarmTrapsPrefix 1 }

        hwRectifierFaultAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier Fault alarm resolved.Its correlation binding parameters: Site ID, Site name, Site description, NE ID, Alarm name, Alarm single description, Alarm port description, Alarm severity, and Site alarm SN. Additionally, in order to identify the device, rectifier equipment ID and equipment name are also include in VB(variable bondings)."
            ::= { hwSiteAlarmTrapsPrefix 2 }

        hwRectifierAbnormalAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier abnormal alarm, because of communication failure, module protection, or turnoff. Its correlation binding parameters:  
                Site ID, Site name, Site description, NE ID, Alarm name, Alarm single description, Alarm port description, Alarm severity, and Site alarm SN. Additionally, in order to identify the device, rectifier equipment ID and equipment name are also include in VB(variable bondings)."
            ::= { hwSiteAlarmTrapsPrefix 3 }

        hwRectifierAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier abnormal alarm resume. Description.Its correlation binding parameters:  Site ID, Site name, Site description, NE ID, Alarm name, Alarm single description, Alarm port description, Alarm severity, and Site alarm SN. Additionally, in order to identify the device, rectifier equipment ID and equipment name are also include in VB(variable bondings)."
            ::= { hwSiteAlarmTrapsPrefix 4 }

        hwBattLoopBreakAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery loop disconnect. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 5 }

        hwBattLoopBreakAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery loop break alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 6 }

        hwBattLvdAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery disconnect for low voltage. Its correlation binding parameters:  Site ID, Site name, Site description, NE ID, Alarm name, Alarm single description, Alarm port description, Alarm severity, and Site alarm SN. 
                Additionally, in order to identify the device, battery LVD unit equipment ID and equipment name are also include in VB(variable bondings)."
            ::= { hwSiteAlarmTrapsPrefix 7 }

        hwBattLvdAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery LVD alarm resume. Its correlation binding parameters:  Site ID, Site name, Site description, NE ID, Alarm name, Alarm single description, Alarm port description, Alarm severity, and Site alarm SN. Additionally, in order to identify the device, battery LVD unit equipment ID and equipment name are also include in VB(variable bondings)."
            ::= { hwSiteAlarmTrapsPrefix 8 }

        hwBattOverCurrAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Batterys charge in over current. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 9 }

        hwBattOverCurrAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Batterys over current alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 10 }

        hwBattStringTempAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery string temperature is too high or too low. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 11 }

        hwBattStringTempAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery string temperature alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 12 }

        hwBattDischargeAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 13 }

        hwBattDischargeAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 14 }

        hwAcInputAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC absent or AC power off alarms happened. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 15 }

        hwAcInputAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC input alarm resumed. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 16 }

        hwAcVoltAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC voltage too high or too low. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 17 }

        hwAcVoltAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC voltage alarm resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 18 }

        hwDcVoltAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "DC voltage alarm. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 19 }

        hwDcVoltAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "DC voltage alarm resume. Its correlation binding parameters:  Site ID, Site name, Site description, NE ID, Alarm name, Alarm single description, Alarm port description, Alarm severity, and Site alarm SN. Additionally, in order to identify the device, DC equipment ID and equipment name are also include in VB(variable bondings)."
            ::= { hwSiteAlarmTrapsPrefix 20 }

        hwLoadLvdAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Loads disconnect for low voltage. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 21 }

        hwLoadLvdAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load LVD alarm resume. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 22 }

        hwLoadFuseAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load fuse broken down. Its correlation binding parameters:  Site ID, Site name, Site description, NE ID, Alarm name, Alarm single description, Alarm port description, Alarm severity, and Site alarm SN. Additionally, in order to identify the device, load branch equipment ID and equipment name are also include in VB(variable bondings)."
            ::= { hwSiteAlarmTrapsPrefix 23 }

        hwLoadFuseAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load fuse alarm resume. Its correlation binding parameters:  Site ID, Site name, Site description, NE ID, Alarm name, Alarm single description, Alarm port description, Alarm severity, and Site alarm SN. Additionally, in order to identify the device, load branch equipment ID and equipment name are also include in VB(variable bondings)."
            ::= { hwSiteAlarmTrapsPrefix 24 }

        hwEnvTempAlarmTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempFatherEquipname,hwEnvTempSensorOperStatus            }
            STATUS current
            DESCRIPTION
                "Environment temperature is too high or too low. Its correlation binding parameters:  Site ID, Site name, Site description, NE ID, Alarm name, Alarm single description, Alarm port description, Alarm severity, and Site alarm SN. Additionally, in order to identify the device, envirenment temperature sensor equipment ID ,name and father equip name are also include in VB(variable bondings).    "
            ::= { hwSiteAlarmTrapsPrefix 25 }

        hwEnvTempAlarmResumeTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempFatherEquipname,hwEnvTempSensorOperStatus            }
            STATUS current
            DESCRIPTION
                "Environment temperature alarm resume. Its correlation binding parameters:  Site ID, Site name, Site description, NE ID, Alarm name, Alarm single description, Alarm port description, Alarm severity, and Site alarm SN. Additionally, in order to identify the device, envirenment temperature sensor equipment ID, name and father equip name are also include in VB(variable bondings).    "
            ::= { hwSiteAlarmTrapsPrefix 26 }

        hwEnvHumiAlarmTraps NOTIFICATION-TYPE
            OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiFatherEquipname,hwEnvHumiSensorOperStatus            }
            STATUS current
            DESCRIPTION
                "Environment humidity is too high or too low. Its correlation binding parameters:  Site ID, Site name, Site description, NE ID, Alarm name, Alarm single description, Alarm port description, Alarm severity, and Site alarm SN. Additionally, in order to identify the device, envirenment humidity sensor equipment ID, name and father equip nameare also include in VB(variable bondings)."
            ::= { hwSiteAlarmTrapsPrefix 27 }

        hwEnvHumiAlarmResumeTraps NOTIFICATION-TYPE
            OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiFatherEquipname,hwEnvHumiSensorOperStatus            }
            STATUS current
            DESCRIPTION
                "Environment humidity alarm resume. Its correlation binding parameters:  Site ID, Site name, Site description, NE ID, Alarm name, Alarm single description, Alarm port description, Alarm severity, and Site alarm SN. Additionally, in order to identify the device, envirenment humidity sensor equipment ID, name and father equip name are also include in VB(variable bondings)."
            ::= { hwSiteAlarmTrapsPrefix 28 }

        hwSpareDigitalAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Spare digital fault. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 29 }

        hwSpareDigitalAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Spare digital alarm resume.Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 30 }

        hwDoorAlarmTraps NOTIFICATION-TYPE
            OBJECTS { hwAlarmTrapOrdinalNumber,hwAlarmText,hwAlarmLevel,hwAlarmSigDesc,hwSiteName,hwSiteAdminAddr,hwNetIdentifier,hwSiteDescription,hwDoorSensorEquipId,hwDoorEquipName,hwDoorSensorFatherEquipname            }
            STATUS current
            DESCRIPTION
                "Door open. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 31 }

        hwDoorAlarmResumeTraps NOTIFICATION-TYPE
            OBJECTS { hwAlarmTrapOrdinalNumber,hwAlarmText,hwAlarmLevel,hwAlarmSigDesc,hwSiteName,hwSiteAdminAddr,hwNetIdentifier,hwSiteDescription,hwDoorSensorEquipId,hwDoorEquipName,hwDoorSensorFatherEquipname            }
            STATUS current
            DESCRIPTION
                "Door alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 32 }

        hwWaterAlarmTraps NOTIFICATION-TYPE
            OBJECTS { hwAlarmTrapOrdinalNumber,hwAlarmText,hwAlarmLevel,hwAlarmSigDesc,hwSiteName,hwSiteAdminAddr,hwNetIdentifier,hwSiteDescription,hwWaterSensorEquipId,hwWaterEquipName,hwWaterSensorFatherEquipname            }
            STATUS current
            DESCRIPTION
                "Water alarm. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 33 }

        hwWaterAlarmResumeTraps NOTIFICATION-TYPE
            OBJECTS { hwAlarmTrapOrdinalNumber,hwAlarmText,hwAlarmLevel,hwAlarmSigDesc,hwSiteName,hwSiteAdminAddr,hwNetIdentifier,hwSiteDescription,hwWaterSensorEquipId,hwWaterEquipName,hwWaterSensorFatherEquipname            }
            STATUS current
            DESCRIPTION
                "Water alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 34 }

        hwSmokeAlarmTraps NOTIFICATION-TYPE
            OBJECTS { hwAlarmTrapOrdinalNumber,hwAlarmText,hwAlarmLevel,hwAlarmSigDesc,hwSiteName,hwSiteAdminAddr,hwNetIdentifier,hwSiteDescription,hwSmokeSensorEquipId,hwSmokeEquipName,hwSmokeSensorFatherEquipname            }
            STATUS current
            DESCRIPTION
                "Site is on fire, which is detected by smoke sensors. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 35 }

        hwSmokeAlarmResumeTraps NOTIFICATION-TYPE
            OBJECTS { hwAlarmTrapOrdinalNumber,hwAlarmText,hwAlarmLevel,hwAlarmSigDesc,hwSiteName,hwSiteAdminAddr,hwNetIdentifier,hwSiteDescription,hwSmokeSensorEquipId,hwSmokeEquipName,hwSmokeSensorFatherEquipname            }
            STATUS current
            DESCRIPTION
                "Smoke alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 36 }

        hwWireAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Wire alarm.Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 37 }

        hwWireAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Wire alarm resume. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 38 }

        hwAcBreakerAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "AC breaker alarm.Its correlation binding parameters:  Site ID, Site name, Site description, NE ID, Alarm name, Alarm single description, Alarm port description, Alarm severity, and Site alarm SN. Additionally, in order to identify the device, AC distribution unit ID and its name are also include in VB(variable bondings)."
            ::= { hwSiteAlarmTrapsPrefix 39 }

        hwAcBreakerAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "AC breaker alarm resume.Its correlation binding parameters:  Site ID, Site name, Site description, NE ID, Alarm name, Alarm single description, Alarm port description, Alarm severity, and Site alarm SN. Additionally, in order to identify the device, AC distribution unit ID and its name are also include in VB(variable bondings)."
            ::= { hwSiteAlarmTrapsPrefix 40 }

        hwMultiRectFailureAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "More than one rectifier reported fault alarms in the same time. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 41 }

        hwMultiRectFailureAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Multi-rectifiers fault alarm resume. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 42 }

        hwRectRedundAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers work redundantly, in this case that some of rectifiers will going to sleep. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 43 }

        hwRectRedundAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers redundant alarm resume, when the power supply and requirement were in balance. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 44 }

        hwBattUnbalanceAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery works in unbalance state. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 45 }

        hwBattUnbalanceAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery unbalance alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 46 }

        hwAcFreqFaultAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC frequency is fault. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 47 }

        hwAcFreqFaultAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC frequency alarm resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 48 }

        hwXmuSelfFaultAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "There are some fault in XMU itself. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 49 }

        hwXmuSelfFaultAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "XMU fault alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 50 }

        hwRs485CommAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "RS485 communication of monitors disconnect. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 51 }

        hwRs485CommAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "RS485 communication alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 52 }

        hwNetCommAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "Network communication of monitors disconnect. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 53 }

        hwNetCommAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "Network communication alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 54 }

        hwAcOffLongTimeAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC power off for a long time alarms happened. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 55 }

        hwAcOffLongTimeAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC power off for a long time alarms resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 56 }

        hwSpdAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname            }
            STATUS current
            DESCRIPTION
                "Description."
            ::= { hwSiteAlarmTrapsPrefix 57 }

        hwSpdAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname            }
            STATUS current
            DESCRIPTION
                "Description."
            ::= { hwSiteAlarmTrapsPrefix 58 }

        hwBadBatteryTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 59 }

        hwBadBatteryResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 60 }

        hwLvd2DisconnectingTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Description."
            ::= { hwSiteAlarmTrapsPrefix 61 }

        hwLvd2DisconnectingResumeTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Description."
            ::= { hwSiteAlarmTrapsPrefix 62 }

        hwBattHighTempTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 63 }

        hwBattHighTempResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 64 }

        hwBattLowTempTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 65 }

        hwBattLowTempResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 66 }

        hwDcUltraOverVoltageTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 67 }

        hwDcUltraOverVoltageResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 68 }

        hwDcUltraUnderVoltageTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 69 }

        hwDcUltraUnderVoltageResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 70 }

        hwUmiCommFailTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 71 }

        hwUmiCommFailResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 72 }

        hwShortTestFailTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 73 }

        hwShortTestFailResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 74 }

        hwMissingBattTempSensorTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 75 }

        hwMissingBattTempSensorResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 76 }

        hwBattTempSensorFaultTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 77 }

        hwBattTempSensorFaultResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 78 }

        hwAcOverVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 79 }

        hwAcOverVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 80 }

        hwAcUnderVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 81 }

        hwAcUnderVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 82 }

        hwTcuFanAlarmTraps NOTIFICATION-TYPE
            OBJECTS { hwAlarmTrapOrdinalNumber,hwAlarmText,hwAlarmLevel,hwAlarmSigDesc,hwSiteName,hwSiteAdminAddr,hwNetIdentifier,hwSiteDescription,hwFanEquipId,hwFanEquipName,hwFanOperStatus,hwFanFatherEquipName            }
            STATUS current
            DESCRIPTION
                "Description."
            ::= { hwSiteAlarmTrapsPrefix 83 }

        hwTcuFanAlarmResumeTraps NOTIFICATION-TYPE
            OBJECTS { hwAlarmTrapOrdinalNumber,hwAlarmText,hwAlarmLevel,hwAlarmSigDesc,hwSiteName,hwSiteAdminAddr,hwNetIdentifier,hwSiteDescription,hwFanEquipId,hwFanEquipName,hwFanOperStatus,hwFanFatherEquipName            }
            STATUS current
            DESCRIPTION
                "Description."
            ::= { hwSiteAlarmTrapsPrefix 84 }

        hwTcuDcAirAlarmTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus,hwDcAirFatherEquipName            }
            STATUS current
            DESCRIPTION
                "Description."
            ::= { hwSiteAlarmTrapsPrefix 85 }

        hwTcuDcAirAlarmResumeTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus,hwDcAirFatherEquipName            }
            STATUS current
            DESCRIPTION
                "Description."
            ::= { hwSiteAlarmTrapsPrefix 86 }

        hwTripBreakAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Description."
            ::= { hwSiteAlarmTrapsPrefix 87 }

        hwTripBreakAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Description."
            ::= { hwSiteAlarmTrapsPrefix 88 }

        hwTripBatteryCabinetAlarmTraps NOTIFICATION-TYPE
            OBJECTS { hwAlarmTrapOrdinalNumber,hwAlarmText,hwAlarmLevel,hwAlarmSigDesc,hwSiteName,hwSiteAdminAddr,hwNetIdentifier,hwSiteDescription,hwBatteryCabinetEquipId,hwBatteryCabinetEquipName            }
            STATUS current
            DESCRIPTION
                "Description."
            ::= { hwSiteAlarmTrapsPrefix 89 }

        hwTripBattCabAlarmResumeTraps NOTIFICATION-TYPE
            OBJECTS { hwAlarmTrapOrdinalNumber,hwAlarmText,hwAlarmLevel,hwAlarmSigDesc,hwSiteName,hwSiteAdminAddr,hwNetIdentifier,hwSiteDescription,hwBatteryCabinetEquipId,hwBatteryCabinetEquipName            }
            STATUS current
            DESCRIPTION
                "Description."
            ::= { hwSiteAlarmTrapsPrefix 90 }

        hwBattTestAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battary test alarms. Its correlation binding parameters:  Site ID, Site name, Site description, NE ID, Alarm name, Alarm single description, Alarm port description, Alarm severity, and Site alarm SN. Additionally, in order to identify the device, Battary group equipment ID and equipment name are also include in VB(variable bondings)."
            ::= { hwSiteAlarmTrapsPrefix 103 }

        hwBattTestAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battary test alarms resume. Its correlation binding parameters:  Site ID, Site name, Site description, NE ID, Alarm name, Alarm single description, Alarm port description, Alarm severity, and Site alarm SN. Additionally, in order to identify the device, Battary group equipment ID and equipment name are also include in VB(variable bondings)."
            ::= { hwSiteAlarmTrapsPrefix 104 }

        hwBattContactorFaultTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 105 }

        hwBattContactorFaultResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 106 }

        hwBattFuseBreakAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 107 }

        hwBattFuseBreakAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 108 }

        hwDCDAbnormalAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "Description."
            ::= { hwSiteAlarmTrapsPrefix 109 }

        hwDCDAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "Description."
            ::= { hwSiteAlarmTrapsPrefix 110 }

        hwACDAbnormalAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 111 }

        hwACDAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 112 }

        hwLoadOverCurrentAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 113 }

        hwLoadOverCurrentAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 114 }

        hwEOSNoResponseAlarmTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 115 }

        hwEOSNoResponseAlarmResumeTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 116 }

        hwEOSOverLoadAlarmTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 117 }

        hwEOSOverLoadAlarmResumeTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 118 }

        hwInverterAlarmTraps NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName,hwInverterOperStatus            }
            STATUS current
            DESCRIPTION
                "Description."
            ::= { hwSiteAlarmTrapsPrefix 119 }

        hwInveterAlarmResumeTraps NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName,hwInverterOperStatus            }
            STATUS current
            DESCRIPTION
                "Description."
            ::= { hwSiteAlarmTrapsPrefix 120 }

        hwDGAlarmTraps NOTIFICATION-TYPE
            OBJECTS { hwAlarmTrapOrdinalNumber,hwAlarmText,hwAlarmLevel,hwAlarmSigDesc,hwSiteName,hwSiteAdminAddr,hwNetIdentifier,hwSiteDescription,hwDGEquipId,hwDGEquipName            }
            STATUS current
            DESCRIPTION
                "Description."
            ::= { hwSiteAlarmTrapsPrefix 121 }

        hwDGAlarmResumeTraps NOTIFICATION-TYPE
            OBJECTS { hwAlarmTrapOrdinalNumber,hwAlarmText,hwAlarmLevel,hwAlarmSigDesc,hwSiteName,hwSiteAdminAddr,hwNetIdentifier,hwSiteDescription,hwDGEquipId,hwDGEquipName            }
            STATUS current
            DESCRIPTION
                "Description."
            ::= { hwSiteAlarmTrapsPrefix 122 }

        hwSSUSummaryAlarmTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 123 }

        hwSSUSummaryAlarmResumeTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 124 }

        hwSSUAlarmTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName,hwSSUFatherEquipName            }
            STATUS current
            DESCRIPTION
                "Description."
            ::= { hwSiteAlarmTrapsPrefix 125 }

        hwSSUAlarmResumeTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName,hwSSUFatherEquipName            }
            STATUS current
            DESCRIPTION
                "Description."
            ::= { hwSiteAlarmTrapsPrefix 126 }

        hwTemp1SensorAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 127 }

        hwTemp1SensorAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 128 }

        hwTemp2SensorAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 129 }

        hwTemp2SensorAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 130 }

        hwEsduDigitalInputAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU Spare digital fault. Its correlation binding parameters:  Site ID, Site name, Site description, NE ID, Alarm name, Alarm single description, Alarm port description, Alarm severity, and Site alarm SN. Additionally, in order to identify the device, Spare digital equipment ID and equipment name are also include in VB(variable bondings).    "
            ::= { hwSiteAlarmTrapsPrefix 147 }

        hwEsduDigitalInputAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU Spare digital alarm resume.Its correlation binding parameters:  Site ID, Site name, Site description, NE ID, Alarm name, Alarm single description, Alarm port description, Alarm severity, and Site alarm SN. Additionally, in order to identify the device, Spare digital equipment ID and equipment name are also include in VB(variable bondings).    "
            ::= { hwSiteAlarmTrapsPrefix 148 }

        hwEsduDoorOpenAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU door is open."
            ::= { hwSiteAlarmTrapsPrefix 149 }

        hwEsduDoorOpenAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU door open  alarm resumed."
            ::= { hwSiteAlarmTrapsPrefix 150 }

        hwEsduTemp1SensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor is faulty."
            ::= { hwSiteAlarmTrapsPrefix 151 }

        hwEsduTemp1SensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor fault alarm recovers."
            ::= { hwSiteAlarmTrapsPrefix 152 }

        hwEsduTemp1SensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor is missing."
            ::= { hwSiteAlarmTrapsPrefix 153 }

        hwEsduTemp1SensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor missing alarm recovers."
            ::= { hwSiteAlarmTrapsPrefix 154 }

        hwEsduTemp2SensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP2 sensor is faulty."
            ::= { hwSiteAlarmTrapsPrefix 155 }

        hwEsduTemp2SensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor fault alarm recovers."
            ::= { hwSiteAlarmTrapsPrefix 156 }

        hwEsduTemp2SensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor is missing."
            ::= { hwSiteAlarmTrapsPrefix 157 }

        hwEsduTemp2SensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor missing alarm recovers."
            ::= { hwSiteAlarmTrapsPrefix 158 }

        hwEsduBtempSensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor is faulty."
            ::= { hwSiteAlarmTrapsPrefix 159 }

        hwEsduBtempSensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor fault alarm recovers."
            ::= { hwSiteAlarmTrapsPrefix 160 }

        hwEsduBtempSensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor is missing."
            ::= { hwSiteAlarmTrapsPrefix 161 }

        hwEsduBtempSensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor missing alarm recovers."
            ::= { hwSiteAlarmTrapsPrefix 162 }

        hwEsduTemp1AlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 temperature is out of range（too high or too low）. "
            ::= { hwSiteAlarmTrapsPrefix 163 }

        hwEsduTemp1AlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 temperature alarm resume.   "
            ::= { hwSiteAlarmTrapsPrefix 164 }

        hwEsduTemp2AlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 temperature is out of range（too high or too low）. "
            ::= { hwSiteAlarmTrapsPrefix 165 }

        hwEsduTemp2AlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 temperature alarm resume.   "
            ::= { hwSiteAlarmTrapsPrefix 166 }

        hwEsduCommAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The Moniter cannot commuicate with the ESDU."
            ::= { hwSiteAlarmTrapsPrefix 167 }

        hwEsduCommAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The communication between monitor and ESDU recovers."
            ::= { hwSiteAlarmTrapsPrefix 168 }

        hwBatteryLowCapacityAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "The capacity of batteries is low."
            ::= { hwSiteAlarmTrapsPrefix 169 }

        hwBatteryLowCapacityAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "The alarm of low capacity resumed."
            ::= { hwSiteAlarmTrapsPrefix 170 }

        hwBatteryLostAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname            }
            STATUS current
            DESCRIPTION
                "Some battery strings could be lost, when the alarm happened."
            ::= { hwSiteAlarmTrapsPrefix 171 }

        hwBatteryLostAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname            }
            STATUS current
            DESCRIPTION
                "If all the battery strings can be detected, the alarm of battery losting resume."
            ::= { hwSiteAlarmTrapsPrefix 172 }

        hwRectCapacityAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm happened."
            ::= { hwSiteAlarmTrapsPrefix 131 }

        hwRectCapacityAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm Resumed."
            ::= { hwSiteAlarmTrapsPrefix 132 }

        hwPvLostAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                ""
            ::= { hwSiteAlarmTrapsPrefix 181 }

        hwPvLostAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                ""
            ::= { hwSiteAlarmTrapsPrefix 182 }

        hwTcucTempSensorFaultAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient temperature sensor fault alarm happened."
            ::= { hwSiteAlarmTrapsPrefix 133 }

        hwTcucTempSensorFaultAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient temperature sensor fault alarm resumed."
            ::= { hwSiteAlarmTrapsPrefix 134 }

        hwTcucFanFaultAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient fan fault alarm happened."
            ::= { hwSiteAlarmTrapsPrefix 135 }

        hwTcucFanFaultAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient fan fault alarm resumed."
            ::= { hwSiteAlarmTrapsPrefix 136 }

        hwTcucTempAbnormalAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet temperature is too high or too low"
            ::= { hwSiteAlarmTrapsPrefix 137 }

        hwTcucTempAbnormalAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet temperature abnormal alarm resumed."
            ::= { hwSiteAlarmTrapsPrefix 138 }

        hwTcucDoorOpenAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet door is open."
            ::= { hwSiteAlarmTrapsPrefix 139 }

        hwTcucDoorOpenAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient door open  alarm resumed."
            ::= { hwSiteAlarmTrapsPrefix 140 }

        hwTcucSmokeAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient smoke alarm happened."
            ::= { hwSiteAlarmTrapsPrefix 141 }

        hwTcucSmokeAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient smoke alarm resumed"
            ::= { hwSiteAlarmTrapsPrefix 142 }

        hwTcucWaterAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient water alarm happend."
            ::= { hwSiteAlarmTrapsPrefix 143 }

        hwTcucWaterAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient water alarm resumed."
            ::= { hwSiteAlarmTrapsPrefix 144 }

        hwTcucCommFailAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient  failed communicate with the monitor."
            ::= { hwSiteAlarmTrapsPrefix 145 }

        hwTcucCommFailAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient  communication fail alarm resumed."
            ::= { hwSiteAlarmTrapsPrefix 146 }

        hwAtsAlarmTrap NOTIFICATION-TYPE
            OBJECTS { hwAlarmTrapOrdinalNumber,hwAlarmText,hwAlarmLevel,hwAlarmSigDesc,hwSiteName,hwSiteAdminAddr,hwNetIdentifier,hwSiteDescription,hwAtsEquipId,hwAtsEquipName            }
            STATUS current
            DESCRIPTION
                "ATS Alarm. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 187 }

        hwAtsAlarmResumeTrap NOTIFICATION-TYPE
            OBJECTS { hwAlarmTrapOrdinalNumber,hwAlarmText,hwAlarmLevel,hwAlarmSigDesc,hwSiteName,hwSiteAdminAddr,hwNetIdentifier,hwSiteDescription,hwAtsEquipId,hwAtsEquipName            }
            STATUS current
            DESCRIPTION
                "ATS Alarm Resume. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 188 }

        hwInverterTrapTable OBJECT IDENTIFIER ::= { hwSiteAlarmTraps 4 }

        hwInverterTrapPrefix OBJECT IDENTIFIER ::= { hwInverterTrapTable 0 }

        hwInverterCommFailAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 1 }

        hwInverterCommFailAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 2 }

        hwInverterFanFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Fan Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 3 }

        hwInverterFanFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Fan Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 4 }

        hwInverterACOutLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Undervoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 5 }

        hwInverterACOutLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Undervoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 6 }

        hwInverterACOutHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Overvoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 7 }

        hwInverterACOutHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Overvoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 8 }

        hwInverterModFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Fault.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 9 }

        hwInverterModFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Fault Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 10 }

        hwInverterModTempHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too High.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 11 }

        hwInverterModTempHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too High Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 12 }

        hwInverterModTempLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too Low.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 13 }

        hwInverterModTempLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too Low Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 14 }

        hwInvertersACPhaseShortAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Phase Not Ready.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 15 }

        hwInvertersACPhaseShortAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Phase Not Ready Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 16 }

        hwInverterModOffAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Off.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 17 }

        hwInverterModOffAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Off Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 18 }

        hwInverterACInAbnAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Abnormal.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 19 }

        hwInverterACInAbnAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Abnormal Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 20 }

        hwInverterDCInLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Undervoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 21 }

        hwInverteDCInLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Undervoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 22 }

        hwInverterDCInHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Overvoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 23 }

        hwInverterDCInHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Overvoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 24 }

        hwInverterModCommFailAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 25 }

        hwInverterModCommFailAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 26 }

        hwInverterNoACInAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No AC In.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 27 }

        hwInverterNoACInAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No AC In Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 28 }

        hwInverterNoDCInAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No DC In.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 29 }

        hwInverterNoDCInAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No DC In Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 30 }

        hwInverterT2SFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "T2S Fault.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 31 }

        hwInverterT2SFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "T2S Fault Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 32 }

        hwInvertModMissAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Missing Module.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 33 }

        hwInvertModMissAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Missing Module Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 34 }

        hwIboxAlmTrapTable OBJECT IDENTIFIER ::= { hwSiteAlarmTraps 6 }

        hwIboxAlmTrapPrefix OBJECT IDENTIFIER ::= { hwIboxAlmTrapTable 0 }

        hwIboxCommFailAlarmTrap NOTIFICATION-TYPE
            OBJECTS { hwAlarmTrapOrdinalNumber,hwAlarmText,hwAlarmLevel,hwAlarmSigDesc,hwSiteName,hwSiteAdminAddr,hwNetIdentifier,hwSiteDescription,hwIboxEquipId,hwIboxEquipName            }
            STATUS current
            DESCRIPTION
                "Ibox Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIboxAlmTrapPrefix 1 }

        hwIboxCommFailAlarmResumeTrap NOTIFICATION-TYPE
            OBJECTS { hwAlarmTrapOrdinalNumber,hwAlarmText,hwAlarmLevel,hwAlarmSigDesc,hwSiteName,hwSiteAdminAddr,hwNetIdentifier,hwSiteDescription,hwIboxEquipId,hwIboxEquipName            }
            STATUS current
            DESCRIPTION
                "Ibox Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIboxAlmTrapPrefix 2 }

        hwIbatAlmTrapTable OBJECT IDENTIFIER ::= { hwSiteAlarmTraps 7 }

        hwIbatAlmTrapPrefix OBJECT IDENTIFIER ::= { hwIbatAlmTrapTable 0 }

        hwIbatAlarmTrap NOTIFICATION-TYPE
            OBJECTS { hwAlarmTrapOrdinalNumber,hwAlarmText,hwAlarmLevel,hwAlarmSigDesc,hwSiteName,hwSiteAdminAddr,hwNetIdentifier,hwSiteDescription,hwIbatEquipId,hwIbatEquipName            }
            STATUS current
            DESCRIPTION
                "Ibat Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIbatAlmTrapPrefix 1 }

        hwIbatAlarmResumeTrap NOTIFICATION-TYPE
            OBJECTS { hwAlarmTrapOrdinalNumber,hwAlarmText,hwAlarmLevel,hwAlarmSigDesc,hwSiteName,hwSiteAdminAddr,hwNetIdentifier,hwSiteDescription,hwIbatEquipId,hwIbatEquipName            }
            STATUS current
            DESCRIPTION
                "Ibat Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIbatAlmTrapPrefix 2 }

        hwAcAmmeterAlmTrapTable OBJECT IDENTIFIER ::= { hwSiteAlarmTraps 8 }

        hwAcAmmeterAlmTrapPrefix OBJECT IDENTIFIER ::= { hwAcAmmeterAlmTrapTable 0 }

        hwAcAmmeterAlarmTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter.
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 1 }

        hwAcAmmeterAlarmResumeTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter .
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 2 }

        hwCommExBoardAlmTrapTable OBJECT IDENTIFIER ::= { hwSiteAlarmTraps 9 }

        hwCommExBoardAlmTrapPrefix OBJECT IDENTIFIER ::= { hwCommExBoardAlmTrapTable 0 }

        hwCommExBoardCommFailAlarmTrap NOTIFICATION-TYPE
            OBJECTS { hwAlarmTrapOrdinalNumber,hwAlarmText,hwAlarmLevel,hwAlarmSigDesc,hwSiteName,hwSiteAdminAddr,hwNetIdentifier,hwSiteDescription,hwCommExBoardEquipId,hwCommExBoardEquipName            }
            STATUS current
            DESCRIPTION
                "Communication Expansion Board Communication Failure
                Its correlation binding parameters: 
                Site alarm serial number (SN),
                Alarm name,
                Alarm level,
                Site name,
                Site administrant address,
                NE ID,
                Site description,
                Additionally, in order to identify the device, rectifier equipment ID and equipment name are also include in VB(variable bondings)."
            ::= { hwCommExBoardAlmTrapPrefix 1 }

        hwCommExBoardCommFailAlarmResumeTrap NOTIFICATION-TYPE
            OBJECTS { hwAlarmTrapOrdinalNumber,hwAlarmText,hwAlarmLevel,hwAlarmSigDesc,hwSiteName,hwSiteAdminAddr,hwNetIdentifier,hwSiteDescription,hwCommExBoardEquipId,hwCommExBoardEquipName            }
            STATUS current
            DESCRIPTION
                "Communication Expansion Board Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwCommExBoardAlmTrapPrefix 2 }

        hwDGCommExBoardAlmTrapTable OBJECT IDENTIFIER ::= { hwSiteAlarmTraps 10 }

        hwDGCommExBoardAlmTrapPrefix OBJECT IDENTIFIER ::= { hwDGCommExBoardAlmTrapTable 0 }

        hwDGCommExBoardCommFailAlarmTrap NOTIFICATION-TYPE
            OBJECTS { hwAlarmTrapOrdinalNumber,hwAlarmText,hwAlarmLevel,hwAlarmSigDesc,hwSiteName,hwSiteAdminAddr,hwNetIdentifier,hwSiteDescription,hwDGCommExBoardEquipId,hwDGCommExBoardEquipName            }
            STATUS current
            DESCRIPTION
                "DG Comm Ex Board Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwDGCommExBoardAlmTrapPrefix 1 }

        hwDGCommExBoardCommFailAlarmResumeTrap NOTIFICATION-TYPE
            OBJECTS { hwAlarmTrapOrdinalNumber,hwAlarmText,hwAlarmLevel,hwAlarmSigDesc,hwSiteName,hwSiteAdminAddr,hwNetIdentifier,hwSiteDescription,hwDGCommExBoardEquipId,hwDGCommExBoardEquipName            }
            STATUS current
            DESCRIPTION
                "DG Comm Ex Board Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwDGCommExBoardAlmTrapPrefix 2 }

        hwAcbGroupAlmTrapTable OBJECT IDENTIFIER ::= { hwSiteAlarmTraps 2 }

        hwAcbGroupAlmTrapPrefix OBJECT IDENTIFIER ::= { hwAcbGroupAlmTrapTable 0 }

        hwAcbGroupAlarmTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "ACB Group alarm. 
                Its correlation binding parameters: 
                Site alarm serial number (SN),
                Alarm name,
                Alarm level,
                Site name,
                Site administrant address,
                NE ID,
                Site description,
                Additionally, in order to identify the device, equipment ID and equipment name are also include in VB(variable bondings)."
            ::= { hwAcbGroupAlmTrapPrefix 99 }

        hwAcbGroupAlarmResumeTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "ACB Group alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwAcbGroupAlmTrapPrefix 100 }

        hwAcbAlmTrapTable OBJECT IDENTIFIER ::= { hwSiteAlarmTraps 3 }

        hwAcbAlmTrapPrefix OBJECT IDENTIFIER ::= { hwAcbAlmTrapTable 0 }

        hwAcbAlarmTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName,hwAcbFatherEquipname            }
            STATUS current
            DESCRIPTION
                "ACB alarm. 
                Its correlation binding parameters: 
                Site alarm serial number (SN),
                Alarm name,
                Alarm level,
                Site name,
                Site administrant address,
                NE ID,
                Site description,
                Additionally, in order to identify the device, equipment ID and equipment name are also include in VB(variable bondings)."
            ::= { hwAcbAlmTrapPrefix 99 }

        hwAcbAlarmResumeTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName,hwAcbFatherEquipname            }
            STATUS current
            DESCRIPTION
                "ACB alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwAcbAlmTrapPrefix 100 }

        hwElockAlmTrapTable OBJECT IDENTIFIER ::= { hwSiteAlarmTraps 13 }

        hwElockAlmTrapTablePrefix OBJECT IDENTIFIER ::= { hwElockAlmTrapTable 0 }

        hwElockAlarmTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName,hwElockFatherEquipName            }
            STATUS current
            DESCRIPTION
                "/"
            ::= { hwElockAlmTrapTablePrefix 1 }

        hwElockAlarmResumeTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName,hwElockFatherEquipName            }
            STATUS current
            DESCRIPTION
                "/"
            ::= { hwElockAlmTrapTablePrefix 2 }

        hwTemHumAlmTrapTable OBJECT IDENTIFIER ::= { hwSiteAlarmTraps 14 }

        hwTemHumAlmTrapTablePrefix OBJECT IDENTIFIER ::= { hwTemHumAlmTrapTable 0 }

        hwTemHumAlarmTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName,hwTemHumFahterEquipName            }
            STATUS current
            DESCRIPTION
                "/"
            ::= { hwTemHumAlmTrapTablePrefix 1 }

        hwTemHumAlarmResumeTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName,hwTemHumFahterEquipName            }
            STATUS current
            DESCRIPTION
                "/"
            ::= { hwTemHumAlmTrapTablePrefix 2 }

        hwLiBatteryCabinetAlmTrapTable OBJECT IDENTIFIER ::= { hwSiteAlarmTraps 15 }

        hwLiBatteryCabinetAlmTrapTablePrefix OBJECT IDENTIFIER ::= { hwLiBatteryCabinetAlmTrapTable 0 }

        hwLiBatteryCabinetAlarmTrap NOTIFICATION-TYPE
            OBJECTS { hwAlarmTrapOrdinalNumber,hwAlarmText,hwAlarmLevel,hwAlarmSigDesc,hwSiteName,hwSiteAdminAddr,hwNetIdentifier,hwSiteDescription,hwLiBatteryCabinetEquipId,hwLiBatteryCabinetEquipName            }
            STATUS current
            DESCRIPTION
                "/"
            ::= { hwLiBatteryCabinetAlmTrapTablePrefix 1 }

        hwLiBatteryCabinetAlarmResumeTrap NOTIFICATION-TYPE
            OBJECTS { hwAlarmTrapOrdinalNumber,hwAlarmText,hwAlarmLevel,hwAlarmSigDesc,hwSiteName,hwSiteAdminAddr,hwNetIdentifier,hwSiteDescription,hwLiBatteryCabinetEquipId,hwLiBatteryCabinetEquipName            }
            STATUS current
            DESCRIPTION
                "/"
            ::= { hwLiBatteryCabinetAlmTrapTablePrefix 2 }

        hwDcCabinetAlmTrapTable OBJECT IDENTIFIER ::= { hwSiteAlarmTraps 16 }

        hwDcCabinetAlmTrapTablePrefix OBJECT IDENTIFIER ::= { hwDcCabinetAlmTrapTable 0 }

        hwDcCabinetAlarmTrap NOTIFICATION-TYPE
            OBJECTS { hwAlarmTrapOrdinalNumber,hwAlarmText,hwAlarmLevel,hwAlarmSigDesc,hwSiteName,hwSiteAdminAddr,hwNetIdentifier,hwSiteDescription,hwDcCabinetEquipId,hwDcCabinetEquipName            }
            STATUS current
            DESCRIPTION
                "/"
            ::= { hwDcCabinetAlmTrapTablePrefix 1 }

        hwDcCabinetAlarmResumeTrap NOTIFICATION-TYPE
            OBJECTS { hwAlarmTrapOrdinalNumber,hwAlarmText,hwAlarmLevel,hwAlarmSigDesc,hwSiteName,hwSiteAdminAddr,hwNetIdentifier,hwSiteDescription,hwDcCabinetEquipId,hwDcCabinetEquipName            }
            STATUS current
            DESCRIPTION
                "/"
            ::= { hwDcCabinetAlmTrapTablePrefix 2 }

        hwCombinedCabinetAlmTrapTable OBJECT IDENTIFIER ::= { hwSiteAlarmTraps 17 }

        hwCombinedCabinetAlmTrapTablePrefix OBJECT IDENTIFIER ::= { hwCombinedCabinetAlmTrapTable 0 }

        hwCombinedCabinetAlarmTrap NOTIFICATION-TYPE
            OBJECTS { hwAlarmTrapOrdinalNumber,hwAlarmText,hwAlarmLevel,hwAlarmSigDesc,hwSiteName,hwSiteAdminAddr,hwNetIdentifier,hwSiteDescription,hwCombinedCabinetEquipId,hwCombinedCabinetEquipName            }
            STATUS current
            DESCRIPTION
                "/"
            ::= { hwCombinedCabinetAlmTrapTablePrefix 1 }

        hwCombinedCabinetAlarmResumeTrap NOTIFICATION-TYPE
            OBJECTS { hwAlarmTrapOrdinalNumber,hwAlarmText,hwAlarmLevel,hwAlarmSigDesc,hwSiteName,hwSiteAdminAddr,hwNetIdentifier,hwSiteDescription,hwCombinedCabinetEquipId,hwCombinedCabinetEquipName            }
            STATUS current
            DESCRIPTION
                "/"
            ::= { hwCombinedCabinetAlmTrapTablePrefix 2 }

        hwRectifierCabinetAlmTrapTable OBJECT IDENTIFIER ::= { hwSiteAlarmTraps 18 }

        hwRectifierCabinetAlmTrapPrefix OBJECT IDENTIFIER ::= { hwRectifierCabinetAlmTrapTable 0 }

        hwRectifierCabinetAlarmTrap NOTIFICATION-TYPE
            OBJECTS { hwAlarmTrapOrdinalNumber,hwAlarmText,hwAlarmLevel,hwAlarmSigDesc,hwSiteName,hwSiteAdminAddr,hwNetIdentifier,hwSiteDescription,hwRectifierCabinetEquipId,hwRectifierCabinetEquipName            }
            STATUS current
            DESCRIPTION
                "/"
            ::= { hwRectifierCabinetAlmTrapPrefix 1 }

        hwRectifierCabinetAlarmResumeTrap NOTIFICATION-TYPE
            OBJECTS { hwAlarmTrapOrdinalNumber,hwAlarmText,hwAlarmLevel,hwAlarmSigDesc,hwSiteName,hwSiteAdminAddr,hwNetIdentifier,hwSiteDescription,hwRectifierCabinetEquipId,hwRectifierCabinetEquipName            }
            STATUS current
            DESCRIPTION
                "/"
            ::= { hwRectifierCabinetAlmTrapPrefix 2 }

        hwAcCabinetAlmTrapTable OBJECT IDENTIFIER ::= { hwSiteAlarmTraps 19 }

        hwAcCabinetAlmTrapPrefix OBJECT IDENTIFIER ::= { hwAcCabinetAlmTrapTable 0 }

        hwAcCabinetAlarmTrap NOTIFICATION-TYPE
            OBJECTS { hwAlarmTrapOrdinalNumber,hwAlarmText,hwAlarmLevel,hwAlarmSigDesc,hwSiteName,hwSiteAdminAddr,hwNetIdentifier,hwSiteDescription,hwAcCabinetEquipId,hwAcCabinetEquipName            }
            STATUS current
            DESCRIPTION
                "/"
            ::= { hwAcCabinetAlmTrapPrefix 1 }

        hwAcCabinetAlarmResumeTrap NOTIFICATION-TYPE
            OBJECTS { hwAlarmTrapOrdinalNumber,hwAlarmText,hwAlarmLevel,hwAlarmSigDesc,hwSiteName,hwSiteAdminAddr,hwNetIdentifier,hwSiteDescription,hwAcCabinetEquipId,hwAcCabinetEquipName            }
            STATUS current
            DESCRIPTION
                "/"
            ::= { hwAcCabinetAlmTrapPrefix 2 }

        hwLocalDCPowerAlmTrapTable OBJECT IDENTIFIER ::= { hwSiteAlarmTraps 20 }

        hwLocalDCPowerAlmTrapPrefix OBJECT IDENTIFIER ::= { hwLocalDCPowerAlmTrapTable 0 }

        hwLocalDCPowerAlarmTrap NOTIFICATION-TYPE
            OBJECTS { hwAlarmTrapOrdinalNumber,hwAlarmText,hwAlarmLevel,hwAlarmSigDesc,hwSiteName,hwSiteAdminAddr,hwNetIdentifier,hwSiteDescription,hwLocalDCPowerEquipId,hwLocalDCPowerEquipName            }
            STATUS current
            DESCRIPTION
                "The alarm of DC power device lost."
            ::= { hwLocalDCPowerAlmTrapPrefix 1 }

        hwLocalDCPowerAlarmResumeTrap NOTIFICATION-TYPE
            OBJECTS { hwAlarmTrapOrdinalNumber,hwAlarmText,hwAlarmLevel,hwAlarmSigDesc,hwSiteName,hwSiteAdminAddr,hwNetIdentifier,hwSiteDescription,hwLocalDCPowerEquipId,hwLocalDCPowerEquipName            }
            STATUS current
            DESCRIPTION
                "The alarm of DC power device lost resume."
            ::= { hwLocalDCPowerAlmTrapPrefix 2 }

        hwACSamplingUnitAlmTrapTable OBJECT IDENTIFIER ::= { hwSiteAlarmTraps 21 }

        hwACSamplingUnitAlmTrapPrefix OBJECT IDENTIFIER ::= { hwACSamplingUnitAlmTrapTable 0 }

        hwACSamplingUnitAlarmTrap NOTIFICATION-TYPE
            OBJECTS { hwAlarmTrapOrdinalNumber,hwAlarmText,hwAlarmLevel,hwAlarmSigDesc,hwSiteName,hwSiteAdminAddr,hwNetIdentifier,hwSiteDescription,hwACSamplingUnitEquipId,hwACSamplingUnitEquipName            }
            STATUS current
            DESCRIPTION
                "/"
            ::= { hwACSamplingUnitAlmTrapPrefix 1 }

        hwACSamplingUnitAlarmResumeTrap NOTIFICATION-TYPE
            OBJECTS { hwAlarmTrapOrdinalNumber,hwAlarmText,hwAlarmLevel,hwAlarmSigDesc,hwSiteName,hwSiteAdminAddr,hwNetIdentifier,hwSiteDescription,hwACSamplingUnitEquipId,hwACSamplingUnitEquipName            }
            STATUS current
            DESCRIPTION
                "/"
            ::= { hwACSamplingUnitAlmTrapPrefix 2 }

        hwDCSamplingUnitAlmTrapTable OBJECT IDENTIFIER ::= { hwSiteAlarmTraps 22 }

        hwDCSamplingUnitAlmTrapPrefix OBJECT IDENTIFIER ::= { hwDCSamplingUnitAlmTrapTable 0 }

        hwDCSamplingUnitAlarmTrap NOTIFICATION-TYPE
            OBJECTS { hwAlarmTrapOrdinalNumber,hwAlarmText,hwAlarmLevel,hwAlarmSigDesc,hwSiteName,hwSiteAdminAddr,hwNetIdentifier,hwSiteDescription,hwDCSamplingUnitEquipId,hwDCSamplingUnitEquipName            }
            STATUS current
            DESCRIPTION
                "The alarm of DC samping unit."
            ::= { hwDCSamplingUnitAlmTrapPrefix 1 }

        hwDCSamplingUnitAlarmResumeTrap NOTIFICATION-TYPE
            OBJECTS { hwAlarmTrapOrdinalNumber,hwAlarmText,hwAlarmLevel,hwAlarmSigDesc,hwSiteName,hwSiteAdminAddr,hwNetIdentifier,hwSiteDescription,hwDCSamplingUnitEquipId,hwDCSamplingUnitEquipName            }
            STATUS current
            DESCRIPTION
                "The alarm of DC samping unit."
            ::= { hwDCSamplingUnitAlmTrapPrefix 2 }

        hwDCOutputDistributionAlmTrapTable OBJECT IDENTIFIER ::= { hwSiteAlarmTraps 23 }

        hwDCOutputDistributionAlmTrapPrefix OBJECT IDENTIFIER ::= { hwDCOutputDistributionAlmTrapTable 0 }

        hwDCOutputDistributionAlarmTrap NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "The alarm of DC samping unit no response."
            ::= { hwDCOutputDistributionAlmTrapPrefix 1 }

        hwDCOutputDistributionAlarmResumeTrap NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "The alarm of DC samping unit no response resume."
            ::= { hwDCOutputDistributionAlmTrapPrefix 2 }

        hwHWinverterUnitAlmTrapTable OBJECT IDENTIFIER ::= { hwSiteAlarmTraps 24 }

        hwHWinverterUnitAlmTrapPrefix  OBJECT IDENTIFIER ::= { hwHWinverterUnitAlmTrapTable 0 }

        hwHWinverterUnitAlarmTrap NOTIFICATION-TYPE
            OBJECTS { hwAlarmTrapOrdinalNumber,hwAlarmText,hwAlarmLevel,hwAlarmSigDesc,hwSiteName,hwSiteAdminAddr,hwNetIdentifier,hwSiteDescription,hwHWInverterUnitId,hwHWInverterUnitName,hwHWinverterUnitFatherEquipName            }
            STATUS current
            DESCRIPTION
                "HW inverter unit equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWinverterUnitAlmTrapPrefix  1 }

        hwHWinverterUnitAlarmResumeTrap NOTIFICATION-TYPE
            OBJECTS { hwAlarmTrapOrdinalNumber,hwAlarmText,hwAlarmLevel,hwAlarmSigDesc,hwSiteName,hwSiteAdminAddr,hwNetIdentifier,hwSiteDescription,hwHWInverterUnitId,hwHWInverterUnitName,hwHWinverterUnitFatherEquipName            }
            STATUS current
            DESCRIPTION
                "HW inverter unit equipment alarm resume.
                Its correlation binding parameters: 
                Site alarm serial number (SN),
                Alarm name,
                Alarm level,
                Site name,
                Site administrant address,
                NE ID,
                Site description,
                Additionally, in order to identify the device, equipment ID and equipment name are also include in VB(variable bondings)."
            ::= { hwHWinverterUnitAlmTrapPrefix  2 }

        hwECMAlmTrapTable OBJECT IDENTIFIER ::= { hwSiteAlarmTraps 25 }

        hwECMAlmTrapPrefix  OBJECT IDENTIFIER ::= { hwECMAlmTrapTable 0 }

        hwECMAlarmTrap NOTIFICATION-TYPE
            OBJECTS { hwAlarmTrapOrdinalNumber,hwAlarmText,hwAlarmLevel,hwAlarmSigDesc,hwSiteName,hwSiteAdminAddr,hwNetIdentifier,hwSiteDescription,hwECMEquipId,hwECMEquipName,hwECMFatherEquipName            }
            STATUS current
            DESCRIPTION
                "ECM equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwECMAlmTrapPrefix  1 }

        hwECMAlarmResumeTrap NOTIFICATION-TYPE
            OBJECTS { hwAlarmTrapOrdinalNumber,hwAlarmText,hwAlarmLevel,hwAlarmSigDesc,hwSiteName,hwSiteAdminAddr,hwNetIdentifier,hwSiteDescription,hwECMEquipId,hwECMEquipName,hwECMFatherEquipName            }
            STATUS current
            DESCRIPTION
                "ECM equipment alarm resume. 
                Its correlation binding parameters: 
                Site alarm serial number (SN),
                Alarm name,
                Alarm level,
                Site name,
                Site administrant address,
                NE ID,
                Site description,
                Additionally, in order to identify the device, equipment ID and equipment name are also include in VB(variable bondings)."
            ::= { hwECMAlmTrapPrefix  2 }

        hwHWInverterAlmTrapTable OBJECT IDENTIFIER ::= { hwSiteAlarmTraps 26 }

        hwHWInverterAlmTrapPerfix  OBJECT IDENTIFIER ::= { hwHWInverterAlmTrapTable 0 }

        hwHWInverterAlarmTrap NOTIFICATION-TYPE
            OBJECTS { hwAlarmTrapOrdinalNumber,hwAlarmText,hwAlarmLevel,hwAlarmSigDesc,hwSiteName,hwSiteAdminAddr,hwNetIdentifier,hwSiteDescription,hwInverterModuleEquipId,hwInverterModuleEquipName,hwInverterModuleFatherEquipName            }
            STATUS current
            DESCRIPTION
                "HW general equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterAlmTrapPerfix  1 }

        hwHWInverterAlarmResumeTrap NOTIFICATION-TYPE
            OBJECTS { hwAlarmTrapOrdinalNumber,hwAlarmText,hwAlarmLevel,hwAlarmSigDesc,hwSiteName,hwSiteAdminAddr,hwNetIdentifier,hwSiteDescription,hwInverterModuleEquipId,hwInverterModuleEquipName,hwInverterModuleFatherEquipName            }
            STATUS current
            DESCRIPTION
                "HW general alarm resume. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterAlmTrapPerfix  2 }

        hwGeneralEquipAlmTrapTable  OBJECT IDENTIFIER ::= { hwSiteAlarmTraps 27 }

        hwGeneralEquipAlmTrapPrefix OBJECT IDENTIFIER ::= { hwGeneralEquipAlmTrapTable  0 }

        hwGeneralEquipCustomAlarmTrap NOTIFICATION-TYPE
            OBJECTS { hwAlarmTrapOrdinalNumber,hwAlarmText,hwAlarmLevel,hwAlarmSigDesc,hwSiteName,hwSiteAdminAddr,hwNetIdentifier,hwSiteDescription,hwGeneralEquipId,hwGeneralEquipName            }
            STATUS current
            DESCRIPTION
                "General equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwGeneralEquipAlmTrapPrefix 1 }

        hwGeneralEquipCustomAlarmResumeTrap NOTIFICATION-TYPE
            OBJECTS { hwAlarmTrapOrdinalNumber,hwAlarmText,hwAlarmLevel,hwAlarmSigDesc,hwSiteName,hwSiteAdminAddr,hwNetIdentifier,hwSiteDescription,hwGeneralEquipId,hwGeneralEquipName            }
            STATUS current
            DESCRIPTION
                "General alarm resume. 
                Its correlation binding parameters: 
                Site alarm serial number (SN),
                Alarm name,
                Alarm level,
                Site name,
                Site administrant address,
                NE ID,
                Site description,
                Additionally, in order to identify the device, equipment ID and equipment name are also include in VB(variable bondings)."
            ::= { hwGeneralEquipAlmTrapPrefix 2 }

        hwDcAmmeterAlmTrapTable OBJECT IDENTIFIER ::= { hwSiteAlarmTraps 28 }

        hwDcAmmeterAlmTrapPrefix OBJECT IDENTIFIER ::= { hwDcAmmeterAlmTrapTable 0 }

        hwDcAmmeterAlarmTrap NOTIFICATION-TYPE
            OBJECTS { hwAlarmTrapOrdinalNumber,hwAlarmText,hwAlarmLevel,hwAlarmSigDesc,hwSiteName,hwSiteAdminAddr,hwNetIdentifier,hwSiteDescription,hwDcAmmeterEquipId,hwDcAmmeterEquipName            }
            STATUS current
            DESCRIPTION
                "Dc Ammeter alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwDcAmmeterAlmTrapPrefix 1 }

        hwDcAmmeterAlarmResumeTrap NOTIFICATION-TYPE
            OBJECTS { hwAlarmTrapOrdinalNumber,hwAlarmText,hwAlarmLevel,hwAlarmSigDesc,hwSiteName,hwSiteAdminAddr,hwNetIdentifier,hwSiteDescription,hwDcAmmeterEquipId,hwDcAmmeterEquipName            }
            STATUS current
            DESCRIPTION
                "Dc Ammeter alarm resume.   parameters: 
                Site alarm serial number (SN),
                Alarm name,
                Alarm level,
                Site name,
                Site administrant address,
                NE ID,
                Site description,
                Additionally, in order to identify the device, Ac Ammeter  equipment ID and equipment name are also include in VB(variable bondings)."
            ::= { hwDcAmmeterAlmTrapPrefix 2 }

        hwFuelTankAlmTrapTable OBJECT IDENTIFIER ::= { hwSiteAlarmTraps 29 }

        hwFuelTankAlmTrapPrefix OBJECT IDENTIFIER ::= { hwFuelTankAlmTrapTable 0 }

        hwFuelTankAlarmTrap NOTIFICATION-TYPE
            OBJECTS { hwAlarmTrapOrdinalNumber,hwAlarmText,hwAlarmLevel,hwAlarmSigDesc,hwSiteName,hwSiteAdminAddr,hwNetIdentifier,hwSiteDescription,hwFuelTankEquipId,hwFuelTankEquipName            }
            STATUS current
            DESCRIPTION
                "/"
            ::= { hwFuelTankAlmTrapPrefix 1 }

        hwFuelTankAlarmResumeTrap NOTIFICATION-TYPE
            OBJECTS { hwAlarmTrapOrdinalNumber,hwAlarmText,hwAlarmLevel,hwAlarmSigDesc,hwSiteName,hwSiteAdminAddr,hwNetIdentifier,hwSiteDescription,hwFuelTankEquipId,hwFuelTankEquipName            }
            STATUS current
            DESCRIPTION
                "/"
            ::= { hwFuelTankAlmTrapPrefix 2 }

        hwPowerControllerTrapTable OBJECT IDENTIFIER ::= { hwSiteAlarmTraps 30 }

        hwPowerControllerAlmTrapPrefix OBJECT IDENTIFIER ::= { hwPowerControllerTrapTable 0 }

        hwPowerControllerAlarmTrap NOTIFICATION-TYPE
            OBJECTS { hwAlarmTrapOrdinalNumber,hwAlarmText,hwAlarmLevel,hwAlarmSigDesc,hwSiteName,hwSiteAdminAddr,hwNetIdentifier,hwSiteDescription,hwPowerControllerEquipId,hwPowerControllerEquipName            }
            STATUS current
            DESCRIPTION
                "Power Controller alarm. 
                Its correlation binding parameters: 
                Site alarm serial number (SN),
                Alarm name,
                Alarm level,
                Site name,
                Site administrant address,
                NE ID,
                Site description,
                Additionally, in order to identify the device, power Controller equipment ID and equipment name are also include in VB(variable bondings)."
            ::= { hwPowerControllerAlmTrapPrefix 1 }

        hwPowerControllerAlarmResumeTrap NOTIFICATION-TYPE
            OBJECTS { hwAlarmTrapOrdinalNumber,hwAlarmText,hwAlarmLevel,hwAlarmSigDesc,hwSiteName,hwSiteAdminAddr,hwNetIdentifier,hwSiteDescription,hwPowerControllerEquipId,hwPowerControllerEquipName            }
            STATUS current
            DESCRIPTION
                "Power Controller alarm resume.  
                Its correlation binding parameters: 
                Site alarm serial number (SN),
                Alarm name,
                Alarm level,
                Site name,
                Site administrant address,
                NE ID,
                Site description,
                Additionally, in order to identify the device, power Controller  equipment ID and equipment name are also include in VB(variable bondings)."
            ::= { hwPowerControllerAlmTrapPrefix 2 }

        hwMimoGroupTrapTable OBJECT IDENTIFIER ::= { hwSiteAlarmTraps 31 }

        hwMimoGroupAlmTrapPrefix OBJECT IDENTIFIER ::= { hwMimoGroupTrapTable 0 }

        hwMimoGroupAlarmTrap NOTIFICATION-TYPE
            OBJECTS { hwAlarmTrapOrdinalNumber,hwAlarmText,hwAlarmLevel,hwAlarmSigDesc,hwSiteName,hwSiteAdminAddr,hwNetIdentifier,hwSiteDescription,hwMimoGroupEquipId,hwMimoGroupEquipName            }
            STATUS current
            DESCRIPTION
                "Mimo Group alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwMimoGroupAlmTrapPrefix 1 }

        hwMimoGroupAlarmResumeTrap NOTIFICATION-TYPE
            OBJECTS { hwAlarmTrapOrdinalNumber,hwAlarmText,hwAlarmLevel,hwAlarmSigDesc,hwSiteName,hwSiteAdminAddr,hwNetIdentifier,hwSiteDescription,hwMimoGroupEquipId,hwMimoGroupEquipName            }
            STATUS current
            DESCRIPTION
                "Mimo Group alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwMimoGroupAlmTrapPrefix 2 }

        hwMimoTrapTable OBJECT IDENTIFIER ::= { hwSiteAlarmTraps 32 }

        hwMimoAlmTrapPrefix OBJECT IDENTIFIER ::= { hwMimoTrapTable 0 }

        hwMimoAlarmTrap NOTIFICATION-TYPE
            OBJECTS { hwAlarmTrapOrdinalNumber,hwAlarmText,hwAlarmLevel,hwAlarmSigDesc,hwSiteName,hwSiteAdminAddr,hwNetIdentifier,hwSiteDescription,hwMimoEquipId,hwMimoEquipName,hwMimoEquipFatherEquipName            }
            STATUS current
            DESCRIPTION
                "Mimo alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwMimoAlmTrapPrefix 1 }

        hwMimoAlarmResumeTrap NOTIFICATION-TYPE
            OBJECTS { hwAlarmTrapOrdinalNumber,hwAlarmText,hwAlarmLevel,hwAlarmSigDesc,hwSiteName,hwSiteAdminAddr,hwNetIdentifier,hwSiteDescription,hwMimoEquipId,hwMimoEquipName,hwMimoEquipFatherEquipName            }
            STATUS current
            DESCRIPTION
                "Mimo alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwMimoAlmTrapPrefix 2 }

        hwIcbdLoadTrapTable OBJECT IDENTIFIER ::= { hwSiteAlarmTraps 33 }

        hwIcbdLoadAlmTrapPrefix OBJECT IDENTIFIER ::= { hwIcbdLoadTrapTable 0 }

        hwIcbdLoadAlarmTrap NOTIFICATION-TYPE
            OBJECTS { hwAlarmTrapOrdinalNumber,hwAlarmText,hwAlarmLevel,hwAlarmSigDesc,hwSiteName,hwSiteAdminAddr,hwNetIdentifier,hwSiteDescription,hwIcbdLoadEquipId,hwIcbdLoadEquipName,hwIcbdLoadFatherEquipName            }
            STATUS current
            DESCRIPTION
                "Icbd Load alarm. 
                Its correlation binding parameters: 
                Site alarm serial number (SN),
                Alarm name,
                Alarm level,
                Site name,
                Site administrant address,
                NE ID,
                Site description,
                Additionally, in order to identify the device, equipment ID and equipment name are also include in VB(variable bondings)."
            ::= { hwIcbdLoadAlmTrapPrefix 1 }

        hwIcbdLoadAlarmResumeTrap NOTIFICATION-TYPE
            OBJECTS { hwAlarmTrapOrdinalNumber,hwAlarmText,hwAlarmLevel,hwAlarmSigDesc,hwSiteName,hwSiteAdminAddr,hwNetIdentifier,hwSiteDescription,hwIcbdLoadEquipId,hwIcbdLoadEquipName,hwIcbdLoadFatherEquipName            }
            STATUS current
            DESCRIPTION
                "IcbdLoad alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwIcbdLoadAlmTrapPrefix 2 }

        hwSSMGroupAlmTrapTable OBJECT IDENTIFIER ::= { hwSiteAlarmTraps 34 }

        hwSSMGroupAlmTrapPrefix OBJECT IDENTIFIER ::= { hwSSMGroupAlmTrapTable 0 }

        hwSSMGroupAlarmTrap NOTIFICATION-TYPE
            OBJECTS { hwAlarmTrapOrdinalNumber,hwAlarmText,hwAlarmLevel,hwAlarmSigDesc,hwSiteName,hwSiteAdminAddr,hwNetIdentifier,hwSiteDescription,hwSSMGroupEquipId,hwSSMGroupEquipName            }
            STATUS current
            DESCRIPTION
                "SSM group alarm. 
                Its correlation binding parameters: 
                Site alarm serial number (SN),
                Alarm name,
                Alarm level,
                Site name,
                Site administrant address,
                NE ID,
                Site description,
                Additionally, in order to identify the device, equipment ID and equipment name are also include in VB(variable bondings)."
            ::= { hwSSMGroupAlmTrapPrefix 1 }

        hwSSMGroupAlarmResumeTrap NOTIFICATION-TYPE
            OBJECTS { hwAlarmTrapOrdinalNumber,hwAlarmText,hwAlarmLevel,hwAlarmSigDesc,hwSiteName,hwSiteAdminAddr,hwNetIdentifier,hwSiteDescription,hwSSMGroupEquipId,hwSSMGroupEquipName            }
            STATUS current
            DESCRIPTION
                "SSM group alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwSSMGroupAlmTrapPrefix 2 }

        hwSSMAlmTrapTable OBJECT IDENTIFIER ::= { hwSiteAlarmTraps 35 }

        hwSSMAlmTrapPrefix OBJECT IDENTIFIER ::= { hwSSMAlmTrapTable 0 }

        hwSSMAlarmTrap NOTIFICATION-TYPE
            OBJECTS { hwAlarmTrapOrdinalNumber,hwAlarmText,hwAlarmLevel,hwAlarmSigDesc,hwSiteName,hwSiteAdminAddr,hwNetIdentifier,hwSiteDescription,hwSSMEquipId,hwSSMEquipName            }
            STATUS current
            DESCRIPTION
                "SSM alarm. 
                Its correlation binding parameters: 
                Site alarm serial number (SN),
                Alarm name,
                Alarm level,
                Site name,
                Site administrant address,
                NE ID,
                Site description,
                Additionally, in order to identify the device, equipment ID and equipment name are also include in VB(variable bondings)."
            ::= { hwSSMAlmTrapPrefix 1 }

        hwSSMAlarmResumeTrap NOTIFICATION-TYPE
            OBJECTS { hwAlarmTrapOrdinalNumber,hwAlarmText,hwAlarmLevel,hwAlarmSigDesc,hwSiteName,hwSiteAdminAddr,hwNetIdentifier,hwSiteDescription,hwSSMEquipId,hwSSMEquipName            }
            STATUS current
            DESCRIPTION
                "SSM alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwSSMAlmTrapPrefix 2 }

        hwPOEAlmTrapTable OBJECT IDENTIFIER ::= { hwSiteAlarmTraps 36 }

        hwPOEAlmTrapPrefix OBJECT IDENTIFIER ::= { hwPOEAlmTrapTable 0 }

        hwPOEAlarmTrap NOTIFICATION-TYPE
            OBJECTS { hwAlarmTrapOrdinalNumber,hwAlarmText,hwAlarmLevel,hwAlarmSigDesc,hwSiteName,hwSiteAdminAddr,hwNetIdentifier,hwSiteDescription,hwSSMEquipId,hwSSMEquipName            }
            STATUS current
            DESCRIPTION
                "POE alarm. 
                Its correlation binding parameters: 
                Site alarm serial number (SN),
                Alarm name,
                Alarm level,
                Site name,
                Site administrant address,
                NE ID,
                Site description,
                Additionally, in order to identify the device, equipment ID and equipment name are also include in VB(variable bondings)."
            ::= { hwPOEAlmTrapPrefix 1 }

        hwPOEAlarmResumeTrap NOTIFICATION-TYPE
            OBJECTS { hwAlarmTrapOrdinalNumber,hwAlarmText,hwAlarmLevel,hwAlarmSigDesc,hwSiteName,hwSiteAdminAddr,hwNetIdentifier,hwSiteDescription,hwSSMEquipId,hwSSMEquipName            }
            STATUS current
            DESCRIPTION
                "POE alarm resume.  
                Its correlation binding parameters: 
                Site alarm serial number (SN),
                Alarm name,
                Alarm level,
                Site name,
                Site administrant address,
                NE ID,
                Site description,
                Additionally, in order to identify the device, equipment ID and equipment name are also include in VB(variable bondings)."
            ::= { hwPOEAlmTrapPrefix 2 }

        hwHWBypassModuleAlmTrapTable OBJECT IDENTIFIER ::= { hwSiteAlarmTraps 37 }

        hwHWBypassModuleAlmTrapPerfix  OBJECT IDENTIFIER ::= { hwHWBypassModuleAlmTrapTable 0 }

        hwHWBypassModuleAlarmTrap NOTIFICATION-TYPE
            OBJECTS { hwAlarmTrapOrdinalNumber,hwAlarmText,hwAlarmLevel,hwAlarmSigDesc,hwSiteName,hwSiteAdminAddr,hwNetIdentifier,hwSiteDescription,hwBypassModuleEquipId,hwBypassModuleEquipName,hwBypassModuleFatherEquipName            }
            STATUS current
            DESCRIPTION
                "Bypass module alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWBypassModuleAlmTrapPerfix  1 }

        hwHWBypassModuleAlarmResumeTrap NOTIFICATION-TYPE
            OBJECTS { hwAlarmTrapOrdinalNumber,hwAlarmText,hwAlarmLevel,hwAlarmSigDesc,hwSiteName,hwSiteAdminAddr,hwNetIdentifier,hwSiteDescription,hwBypassModuleEquipId,hwBypassModuleEquipName,hwBypassModuleFatherEquipName            }
            STATUS current
            DESCRIPTION
                "Bypass module resume.  
                Its correlation binding parameters: 
                Site alarm serial number (SN),
                Alarm name,
                Alarm level,
                Site name,
                Site administrant address,
                NE ID,
                Site description,
                Additionally, in order to identify the device, equipment ID and equipment name are also include in VB(variable bondings)."
            ::= { hwHWBypassModuleAlmTrapPerfix  2 }

        hwUserEquipmentAlmTrapTable OBJECT IDENTIFIER ::= { hwSiteAlarmTraps 47 }

        hwUserEquipmentAlmTrapPerfix OBJECT IDENTIFIER ::= { hwUserEquipmentAlmTrapTable 0 }

        hwUserEquipmentAlarmTrap NOTIFICATION-TYPE
            OBJECTS { hwAlarmTrapOrdinalNumber,hwAlarmText,hwAlarmLevel,hwAlarmSigDesc,hwSiteName,hwSiteAdminAddr,hwNetIdentifier,hwSiteDescription,hwUserEquipmentEquipID,hwUserEquipmentEquipName            }
            STATUS current
            DESCRIPTION
                "Bypass module alarm. 
                Its correlation binding parameters: 
                Site alarm serial number (SN),
                Alarm name,
                Alarm level,
                Site name,
                Site administrant address,
                NE ID,
                Site description,
                Additionally, in order to identify the device, equipment ID and equipment name are also include in VB(variable bondings)."
            ::= { hwUserEquipmentAlmTrapPerfix 1 }

        hwUserEquipmentAlarmResumeTrap NOTIFICATION-TYPE
            OBJECTS { hwAlarmTrapOrdinalNumber,hwAlarmText,hwAlarmLevel,hwAlarmSigDesc,hwSiteName,hwSiteAdminAddr,hwNetIdentifier,hwSiteDescription,hwUserEquipmentEquipID,hwUserEquipmentEquipName            }
            STATUS current
            DESCRIPTION
                "Bypass module resume.  
                Its correlation binding parameters: 
                Site alarm serial number (SN),
                Alarm name,
                Alarm level,
                Site name,
                Site administrant address,
                NE ID,
                Site description,
                Additionally, in order to identify the device, equipment ID and equipment name are also include in VB(variable bondings)."
            ::= { hwUserEquipmentAlmTrapPerfix 2 }

        hwDCDBAlmTrapTable OBJECT IDENTIFIER ::= { hwSiteAlarmTraps 40 }

        hwDCDBAlmTrapPerfix OBJECT IDENTIFIER ::= { hwDCDBAlmTrapTable 0 }

        hwDCDBAlarmTrap NOTIFICATION-TYPE
            OBJECTS { hwAlarmTrapOrdinalNumber,hwAlarmText,hwAlarmLevel,hwAlarmSigDesc,hwSiteName,hwSiteAdminAddr,hwNetIdentifier,hwSiteDescription,hwDCDBEquipId,hwDCDBEquipName            }
            STATUS current
            DESCRIPTION
                "DCDB module alarm. 
                Its correlation binding parameters: 
                Site alarm serial number (SN),
                Alarm name,
                Alarm level,
                Site name,
                Site administrant address,
                NE ID,
                Site description,
                Additionally, in order to identify the device, equipment ID and equipment name are also include in VB(variable bondings)."
            ::= { hwDCDBAlmTrapPerfix 1 }

        hwDCDBAlarmResumeTrap NOTIFICATION-TYPE
            OBJECTS { hwAlarmTrapOrdinalNumber,hwAlarmText,hwAlarmLevel,hwAlarmSigDesc,hwSiteName,hwSiteAdminAddr,hwNetIdentifier,hwSiteDescription,hwDCDBEquipId,hwDCDBEquipName            }
            STATUS current
            DESCRIPTION
                "DCDB module resume.  
                Its correlation binding parameters: 
                Site alarm serial number (SN),
                Alarm name,
                Alarm level,
                Site name,
                Site administrant address,
                NE ID,
                Site description,
                Additionally, in order to identify the device, equipment ID and equipment name are also include in VB(variable bondings)."
            ::= { hwDCDBAlmTrapPerfix 2 }

        hwIDCDUAlmTrapTable OBJECT IDENTIFIER ::= { hwSiteAlarmTraps 41 }

        hwIDCDUAlmTrapPerfix OBJECT IDENTIFIER ::= { hwIDCDUAlmTrapTable 0 }

        hwIDCDUAlarmTrap NOTIFICATION-TYPE
            OBJECTS { hwAlarmTrapOrdinalNumber,hwAlarmText,hwAlarmLevel,hwAlarmSigDesc,hwSiteName,hwSiteAdminAddr,hwNetIdentifier,hwSiteDescription,hwIDCDUEquipId,hwIDCDUEquipName            }
            STATUS current
            DESCRIPTION
                "IDCDU module alarm. 
                Its correlation binding parameters: 
                Site alarm serial number (SN),
                Alarm name,
                Alarm level,
                Site name,
                Site administrant address,
                NE ID,
                Site description,
                Additionally, in order to identify the device, equipment ID and equipment name are also include in VB(variable bondings)."
            ::= { hwIDCDUAlmTrapPerfix 1 }

        hwIDCDUAlarmResumeTrap NOTIFICATION-TYPE
            OBJECTS { hwAlarmTrapOrdinalNumber,hwAlarmText,hwAlarmLevel,hwAlarmSigDesc,hwSiteName,hwSiteAdminAddr,hwNetIdentifier,hwSiteDescription,hwIDCDUEquipId,hwIDCDUEquipName            }
            STATUS current
            DESCRIPTION
                "IDCDU module resume.  
                Its correlation binding parameters: 
                Site alarm serial number (SN),
                Alarm name,
                Alarm level,
                Site name,
                Site administrant address,
                NE ID,
                Site description,
                Additionally, in order to identify the device, equipment ID and equipment name are also include in VB(variable bondings)."
            ::= { hwIDCDUAlmTrapPerfix 2 }

        hwDCDC24VGroupAlmTrapTable OBJECT IDENTIFIER ::= { hwSiteAlarmTraps 42 }

        hwDCDC24VGroupAlmTrapPerfix OBJECT IDENTIFIER ::= { hwDCDC24VGroupAlmTrapTable 0 }

        hwDCDC24VGroupAlmTrap NOTIFICATION-TYPE
            OBJECTS { hwAlarmTrapOrdinalNumber,hwAlarmText,hwAlarmLevel,hwAlarmSigDesc,hwSiteName,hwSiteAdminAddr,hwNetIdentifier,hwSiteDescription,hwDCDCGroupEquipID,hwDCDCGroupEquipName            }
            STATUS current
            DESCRIPTION
                "DCDC 24V Group Alarm Trap. 
                Its correlation binding parameters: 
                Site alarm serial number (SN),
                Alarm name,
                Alarm level,
                Site name,
                Site administrant address,
                NE ID,
                Site description,
                Additionally, in order to identify the device, equipment ID and equipment name are also include in VB(variable bondings)."
            ::= { hwDCDC24VGroupAlmTrapPerfix 1 }

        hwDCDC24VGroupAlmResumeTrap NOTIFICATION-TYPE
            OBJECTS { hwAlarmTrapOrdinalNumber,hwAlarmText,hwAlarmLevel,hwAlarmSigDesc,hwSiteName,hwSiteAdminAddr,hwNetIdentifier,hwSiteDescription,hwDCDCGroupEquipID,hwDCDCGroupEquipName            }
            STATUS current
            DESCRIPTION
                "DCDC 24V Group Alarm Resume Trap.  
                Its correlation binding parameters: 
                Site alarm serial number (SN),
                Alarm name,
                Alarm level,
                Site name,
                Site administrant address,
                NE ID,
                Site description,
                Additionally, in order to identify the device, equipment ID and equipment name are also include in VB(variable bondings)."
            ::= { hwDCDC24VGroupAlmTrapPerfix 2 }

        hwDCDC24VEquipAlmTrapTable OBJECT IDENTIFIER ::= { hwSiteAlarmTraps 43 }

        hwDCDC24VEquipAlmTrapPerfix OBJECT IDENTIFIER ::= { hwDCDC24VEquipAlmTrapTable 0 }

        hwDCDC24VEquipAlmTrap NOTIFICATION-TYPE
            OBJECTS { hwAlarmTrapOrdinalNumber,hwAlarmText,hwAlarmLevel,hwAlarmSigDesc,hwSiteName,hwSiteAdminAddr,hwNetIdentifier,hwSiteDescription,hwDCDC24VEquipID,hwDCDC24VEquipName            }
            STATUS current
            DESCRIPTION
                "DCDC 24V Eauipment Alarm Trap.
                Its correlation binding parameters: 
                Site alarm serial number (SN),
                Alarm name,
                Alarm level,
                Site name,
                Site administrant address,
                NE ID,
                Site description,
                Additionally, in order to identify the device, equipment ID and equipment name are also include in VB(variable bondings)."
            ::= { hwDCDC24VEquipAlmTrapPerfix 1 }

        hwDCDC24VEquipAlmResumeTrap NOTIFICATION-TYPE
            OBJECTS { hwAlarmTrapOrdinalNumber,hwAlarmText,hwAlarmLevel,hwAlarmSigDesc,hwSiteName,hwSiteAdminAddr,hwNetIdentifier,hwSiteDescription,hwDCDC24VEquipID,hwDCDC24VEquipName            }
            STATUS current
            DESCRIPTION
                "DCDC 24V Eauipment Alarm Resume Trap. 
                Its correlation binding parameters: 
                Site alarm serial number (SN),
                Alarm name,
                Alarm level,
                Site name,
                Site administrant address,
                NE ID,
                Site description,
                Additionally, in order to identify the device, equipment ID and equipment name are also include in VB(variable bondings)."
            ::= { hwDCDC24VEquipAlmTrapPerfix 2 }

        hwPVAdapterGroupAlmTrapTable OBJECT IDENTIFIER ::= { hwSiteAlarmTraps 39 }

        hwPVAdapterGroupAlmTrapPerfix  OBJECT IDENTIFIER ::= { hwPVAdapterGroupAlmTrapTable 0 }

        hwPVAdapterGroupAlarmTrap NOTIFICATION-TYPE
            OBJECTS { hwAlarmTrapOrdinalNumber,hwAlarmText,hwAlarmLevel,hwAlarmSigDesc,hwSiteName,hwSiteAdminAddr,hwNetIdentifier,hwSiteDescription,hwPVAdapterGroupEquipId            }
            STATUS current
            DESCRIPTION
                "PV Adapter alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwPVAdapterGroupAlmTrapPerfix  1 }

        hwPVAdapterGroupAlarmResumeTrap NOTIFICATION-TYPE
            OBJECTS { hwAlarmTrapOrdinalNumber,hwAlarmText,hwAlarmLevel,hwAlarmSigDesc,hwSiteName,hwSiteAdminAddr,hwNetIdentifier,hwSiteDescription,hwPVAdapterGroupEquipId            }
            STATUS current
            DESCRIPTION
                "PV Adapter alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwPVAdapterGroupAlmTrapPerfix  2 }

        hwPVAdapterAlmTrapTable OBJECT IDENTIFIER ::= { hwSiteAlarmTraps 38 }

        hwPVAdapterAlmTrapPerfix  OBJECT IDENTIFIER ::= { hwPVAdapterAlmTrapTable 0 }

        hwPVAdapterAlarmTrap NOTIFICATION-TYPE
            OBJECTS { hwAlarmTrapOrdinalNumber,hwAlarmText,hwAlarmLevel,hwAlarmSigDesc,hwSiteName,hwSiteAdminAddr,hwNetIdentifier,hwSiteDescription,hwPVAdapterEquipId,hwPVAdapterEquipName            }
            STATUS current
            DESCRIPTION
                "PV Adapter alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwPVAdapterAlmTrapPerfix  1 }

        hwPVAdapterAlarmResumeTrap NOTIFICATION-TYPE
            OBJECTS { hwAlarmTrapOrdinalNumber,hwAlarmText,hwAlarmLevel,hwAlarmSigDesc,hwSiteName,hwSiteAdminAddr,hwNetIdentifier,hwSiteDescription,hwPVAdapterEquipId,hwPVAdapterEquipName            }
            STATUS current
            DESCRIPTION
                "PV Adapter alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwPVAdapterAlmTrapPerfix  2 }

        hwNaradaBattEquipAlmTrapTable OBJECT IDENTIFIER ::= { hwSiteAlarmTraps 44 }

        hwNaradaBattEquipAlmTrapPerfix OBJECT IDENTIFIER ::= { hwNaradaBattEquipAlmTrapTable 0 }

        hwNaradaBattEquipAlmTrap NOTIFICATION-TYPE
            OBJECTS { hwAlarmTrapOrdinalNumber,hwAlarmText,hwAlarmLevel,hwAlarmSigDesc,hwSiteName,hwSiteAdminAddr,hwNetIdentifier,hwSiteDescription,hwNaradaBattEquipId,hwNaradaBattEquipName            }
            STATUS current
            DESCRIPTION
                "Narada battary alarm. 
                Its correlation binding parameters: 
                Site alarm serial number (SN),
                Alarm name,
                Alarm level,
                Site name,
                Site administrant address,
                NE ID,
                Site description,
                Additionally, in order to identify the device, equipment ID and equipment name are also include in VB(variable bondings)."
            ::= { hwNaradaBattEquipAlmTrapPerfix 1 }

        hwNaradaBattEquipAlmResumeTrap NOTIFICATION-TYPE
            OBJECTS { hwAlarmTrapOrdinalNumber,hwAlarmText,hwAlarmLevel,hwAlarmSigDesc,hwSiteName,hwSiteAdminAddr,hwNetIdentifier,hwSiteDescription,hwNaradaBattEquipId,hwNaradaBattEquipName            }
            STATUS current
            DESCRIPTION
                "Narada battary alarm resume.
                Its correlation binding parameters: 
                Site alarm serial number (SN),
                Alarm name,
                Alarm level,
                Site name,
                Site administrant address,
                NE ID,
                Site description,
                Additionally, in order to identify the device, equipment ID and equipment name are also include in VB(variable bondings)."
            ::= { hwNaradaBattEquipAlmTrapPerfix 2 }

        hwThirdPartyLitBattEquipAlmTrapTable OBJECT IDENTIFIER ::= { hwSiteAlarmTraps 45 }

        hwThirdPartyLitBattEquipAlmTrapPerfix OBJECT IDENTIFIER ::= { hwThirdPartyLitBattEquipAlmTrapTable 0 }

        hwThirdPartyLitBattEquipAlmTrap NOTIFICATION-TYPE
            OBJECTS { hwAlarmTrapOrdinalNumber,hwAlarmText,hwAlarmLevel,hwAlarmSigDesc,hwSiteName,hwSiteAdminAddr,hwNetIdentifier,hwSiteDescription,hw3rdPartyBatEquipId,hw3rdPartyBatEquipName            }
            STATUS current
            DESCRIPTION
                "Third-party lithium battary alarm. 
                Its correlation binding parameters: 
                Site alarm serial number (SN),
                Alarm name,
                Alarm level,
                Site name,
                Site administrant address,
                NE ID,
                Site description,
                Additionally, in order to identify the device, equipment ID and equipment name are also include in VB(variable bondings)."
            ::= { hwThirdPartyLitBattEquipAlmTrapPerfix 1 }

        hwThirdPartyLitBattEquipAlmResumeTrap NOTIFICATION-TYPE
            OBJECTS { hwAlarmTrapOrdinalNumber,hwAlarmText,hwAlarmLevel,hwAlarmSigDesc,hwSiteName,hwSiteAdminAddr,hwNetIdentifier,hwSiteDescription,hw3rdPartyBatEquipId,hw3rdPartyBatEquipName            }
            STATUS current
            DESCRIPTION
                "Third-party lithium battary alarm resume.
                Its correlation binding parameters: 
                Site alarm serial number (SN),
                Alarm name,
                Alarm level,
                Site name,
                Site administrant address,
                NE ID,
                Site description,
                Additionally, in order to identify the device, equipment ID and equipment name are also include in VB(variable bondings)."
            ::= { hwThirdPartyLitBattEquipAlmTrapPerfix 2 }

        hwThirdPartyAcMeterAlmTrapTable OBJECT IDENTIFIER ::= { hwSiteAlarmTraps 46 }

        hwThirdPartyAcMeterAlmTrapPerfix OBJECT IDENTIFIER ::= { hwThirdPartyAcMeterAlmTrapTable 0 }

        hwThirdPartyAcMeterAlmTrap NOTIFICATION-TYPE
            OBJECTS { hwAlarmTrapOrdinalNumber,hwAlarmText,hwAlarmLevel,hwAlarmSigDesc,hwSiteName,hwSiteAdminAddr,hwNetIdentifier,hwSiteDescription,hwThirdPartyAcMeterEquipId,hwThirdPartyAcMeterEquipName            }
            STATUS current
            DESCRIPTION
                "SDM630 AcAmmeter alarm. 
                Its correlation binding parameters: 
                Site alarm serial number (SN),
                Alarm name,
                Alarm level,
                Site name,
                Site administrant address,
                NE ID,
                Site description,
                Additionally, in order to identify the device, equipment ID and equipment name are also include in VB(variable bondings)."
            ::= { hwThirdPartyAcMeterAlmTrapPerfix 1 }

        hwThirdPartyAcMeterAlmResumeTrap NOTIFICATION-TYPE
            OBJECTS { hwAlarmTrapOrdinalNumber,hwAlarmText,hwAlarmLevel,hwAlarmSigDesc,hwSiteName,hwSiteAdminAddr,hwNetIdentifier,hwSiteDescription,hwThirdPartyAcMeterEquipId,hwThirdPartyAcMeterEquipName            }
            STATUS current
            DESCRIPTION
                "SDM630 AcAmmeter alarm resume.   parameters: 
                Site alarm serial number (SN),
                Alarm name,
                Alarm level,
                Site name,
                Site administrant address,
                NE ID,
                Site description,
                Additionally, in order to identify the device, equipment ID and equipment name are also include in VB(variable bondings)."
            ::= { hwThirdPartyAcMeterAlmTrapPerfix 2 }

        hwSiteDevicesTraps OBJECT IDENTIFIER ::= { hwSiteMonitorMIBTraps 2 }

        hwDevicesTrapsPrefix OBJECT IDENTIFIER ::= { hwSiteDevicesTraps 0 }

        hwRectifiersInslotChange NOTIFICATION-TYPE
            OBJECTS { hwDeviceTrapOrdinalNumber,hwSiteName,hwSiteAdminAddr,hwNetIdentifier,hwSiteDescription,hwRectEquipId,hwRectEquipName,hwRectOperStatus            }
            STATUS current
            DESCRIPTION
                "When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
                  This trap is the unique trigger condition that causes the NMS to add or delete entries to or from hwRectConfigTable or hwRectOperTable.
                "
            ::= { hwDevicesTrapsPrefix 1 }

        hwBatterysInslotChange NOTIFICATION-TYPE
            OBJECTS { hwDeviceTrapOrdinalNumber,hwSiteName,hwSiteAdminAddr,hwNetIdentifier,hwSiteDescription,hwBattStringEquipId,hwBattStringEquipName,hwBattStringOperStatus            }
            STATUS current
            DESCRIPTION
                "When the presence status of a battery string changes, the node reports an event. Then the NMS adds or deletes the corresponding entry to or from hwBatttConfigTable or hwBatttOperTable. The bound information includes the site address, site name, site description, and NE identifier. 
                In addition, the ID, name, and status of the battery string are bound to identify the specific battery string and its operation type. 
                When an entry is added, the device status is reported as normal (1); 
                when an entry is deleted, the device status is reported as loopBreak (4).
                  This trap is the unique trigger condition that causes the NMS to add or delete entries to or from hwBatttConfigTable or hwBatttOperTable."
            ::= { hwDevicesTrapsPrefix 2 }

        hwBattTestRecordsAdd NOTIFICATION-TYPE
            OBJECTS { hwDeviceTrapOrdinalNumber,hwSiteName,hwSiteAdminAddr,hwNetIdentifier,hwSiteDescription            }
            STATUS current
            DESCRIPTION
                "After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
                  This trap is the unique trigger condition that causes the NMS to add entries from hwBattsTestResultTable.
                  The battery test table allows you only to add entries."
            ::= { hwDevicesTrapsPrefix 3 }

        hwEnvTempSensInslotChange NOTIFICATION-TYPE
            OBJECTS { hwDeviceTrapOrdinalNumber,hwSiteName,hwSiteAdminAddr,hwNetIdentifier,hwSiteDescription,hwEnvTempEquipId,hwEnvTempEquipName,hwEnvTempSensorOperStatus            }
            STATUS current
            DESCRIPTION
                "When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
                  This trap is the unique trigger condition that causes the NMS to add or delete entries to or from hwEnvTempSensorTable."
            ::= { hwDevicesTrapsPrefix 4 }

        hwEnvHumiSensInslotChange NOTIFICATION-TYPE
            OBJECTS { hwDeviceTrapOrdinalNumber,hwSiteName,hwSiteAdminAddr,hwNetIdentifier,hwSiteDescription,hwEnvHumiEquipId,hwEnvHumiEquipName,hwEnvHumiSensorOperStatus            }
            STATUS current
            DESCRIPTION
                "When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
                  This trap is the unique trigger condition that causes the NMS to add or delete entries to or from hwEnvHumiSensorTable."
            ::= { hwDevicesTrapsPrefix 5 }

        hwPDEsInslotChange NOTIFICATION-TYPE
            OBJECTS { hwDeviceTrapOrdinalNumber,hwSiteName,hwSiteAdminAddr,hwNetIdentifier,hwSiteDescription            }
            STATUS current
            DESCRIPTION
                "Description."
            ::= { hwDevicesTrapsPrefix 6 }

        hwInvertersInslotChange NOTIFICATION-TYPE
            OBJECTS { hwDeviceTrapOrdinalNumber,hwSiteName,hwSiteAdminAddr,hwNetIdentifier,hwSiteDescription,hwInverterEquipId,hwInverterEquipName,hwInverterOperStatus            }
            STATUS current
            DESCRIPTION
                "Description."
            ::= { hwDevicesTrapsPrefix 7 }

        hwSiteStatusTrap OBJECT IDENTIFIER ::= { hwSiteMonitorMIBTraps 3 }

        hwSiteStatusTrapPrefix OBJECT IDENTIFIER ::= { hwSiteStatusTrap 0 }

        hwAcInputFaultTrap NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus,hwAcInputStatus            }
            STATUS current
            DESCRIPTION
                ""
            ::= { hwSiteStatusTrapPrefix 1 }

        hwRectifierFaultTrap NOTIFICATION-TYPE
            OBJECTS { hwAlarmTrapOrdinalNumber,hwAlarmText,hwAlarmLevel,hwAlarmSigDesc,hwSiteName,hwSiteAdminAddr,hwNetIdentifier,hwSiteDescription,hwRectifierStatus            }
            STATUS current
            DESCRIPTION
                ""
            ::= { hwSiteStatusTrapPrefix 2 }

        hwBatteryDischargeTrap NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName,hwBatteryDischarge            }
            STATUS current
            DESCRIPTION
                ""
            ::= { hwSiteStatusTrapPrefix 3 }

        hwBatteryLowVoltageTrap NOTIFICATION-TYPE
            OBJECTS { hwAlarmTrapOrdinalNumber,hwAlarmText,hwAlarmLevel,hwAlarmSigDesc,hwSiteName,hwSiteAdminAddr,hwNetIdentifier,hwSiteDescription,hwBatteryLowVoltage            }
            STATUS current
            DESCRIPTION
                ""
            ::= { hwSiteStatusTrapPrefix 4 }

        hwBatteryUltraLowVoltageTrap NOTIFICATION-TYPE
            OBJECTS { hwAlarmTrapOrdinalNumber,hwAlarmText,hwAlarmLevel,hwAlarmSigDesc,hwSiteName,hwSiteAdminAddr,hwNetIdentifier,hwSiteDescription,hwBatteryUltraLowVoltage            }
            STATUS current
            DESCRIPTION
                ""
            ::= { hwSiteStatusTrapPrefix 5 }

        hwBatteryDisconnectTrap NOTIFICATION-TYPE
            OBJECTS { hwAlarmTrapOrdinalNumber,hwAlarmText,hwAlarmLevel,hwAlarmSigDesc,hwSiteName,hwSiteAdminAddr,hwNetIdentifier,hwSiteDescription,hwBatteryDisconnect            }
            STATUS current
            DESCRIPTION
                ""
            ::= { hwSiteStatusTrapPrefix 6 }

        hwFuseBrokenTrap NOTIFICATION-TYPE
            OBJECTS { hwAlarmTrapOrdinalNumber,hwAlarmText,hwAlarmLevel,hwAlarmSigDesc,hwSiteName,hwSiteAdminAddr,hwNetIdentifier,hwSiteDescription,hwFuseBroken            }
            STATUS current
            DESCRIPTION
                ""
            ::= { hwSiteStatusTrapPrefix 7 }

        hwLowRecitiferCapacityTrap NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName,hwLowRecitiferCapacity            }
            STATUS current
            DESCRIPTION
                ""
            ::= { hwSiteStatusTrapPrefix 8 }

        hwBatteryTestNegativeTrap NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName,hwBatteryTestNegative            }
            STATUS current
            DESCRIPTION
                ""
            ::= { hwSiteStatusTrapPrefix 9 }

        hwUrgentAlarmTrap NOTIFICATION-TYPE
            OBJECTS { hwAlarmTrapOrdinalNumber,hwAlarmText,hwAlarmLevel,hwAlarmSigDesc,hwSiteName,hwSiteAdminAddr,hwNetIdentifier,hwSiteDescription,hwUrgentAlarmStatus            }
            STATUS current
            DESCRIPTION
                ""
            ::= { hwSiteStatusTrapPrefix 10 }

        hwNonurgentAlarmTrap NOTIFICATION-TYPE
            OBJECTS { hwAlarmTrapOrdinalNumber,hwAlarmText,hwAlarmLevel,hwAlarmSigDesc,hwSiteName,hwSiteAdminAddr,hwNetIdentifier,hwSiteDescription,hwNonurgentAlarmStatus            }
            STATUS current
            DESCRIPTION
                ""
            ::= { hwSiteStatusTrapPrefix 11 }

        hwXmuModuleFaultAlarmTraps NOTIFICATION-TYPE
            OBJECTS { hwAlarmTrapOrdinalNumber,hwAlarmText,hwAlarmLevel,hwAlarmSigDesc,hwSiteName,hwSiteAdminAddr,hwNetIdentifier,hwSiteDescription,hwXmuModuleFaultAlarmStatus            }
            STATUS current
            DESCRIPTION
                ""
            ::= { hwSiteStatusTrapPrefix 12 }

        hwLvdDisabledAlarmTraps NOTIFICATION-TYPE
            OBJECTS { hwAlarmTrapOrdinalNumber,hwAlarmText,hwAlarmLevel,hwAlarmSigDesc,hwSiteName,hwSiteAdminAddr,hwNetIdentifier,hwSiteDescription,hwLvdDisabledAlarmStatus            }
            STATUS current
            DESCRIPTION
                ""
            ::= { hwSiteStatusTrapPrefix 13 }

        hwRectMissingAlarmTraps NOTIFICATION-TYPE
            OBJECTS { hwAlarmTrapOrdinalNumber,hwAlarmText,hwAlarmLevel,hwAlarmSigDesc,hwSiteName,hwSiteAdminAddr,hwNetIdentifier,hwSiteDescription,hwRectMissingAlarmStatus            }
            STATUS current
            DESCRIPTION
                ""
            ::= { hwSiteStatusTrapPrefix 14 }

        hwSiteEquip OBJECT IDENTIFIER ::= { hwSiteMonitorMIB 3 }

        hwSiteCameraTable OBJECT-TYPE
            SYNTAX SEQUENCE OF HwSiteCameraEntry
            MAX-ACCESS not-accessible
             STATUS current
             DESCRIPTION
                "/"
            ::= { hwSiteEquip 1 }

        hwSiteCameraEntry OBJECT-TYPE
                        SYNTAX HwSiteCameraEntry
            MAX-ACCESS not-accessible
             STATUS current
             DESCRIPTION
                "/"
            INDEX { hwSiteCameraIp }
            ::= { hwSiteCameraTable 1 }

        HwSiteCameraEntry            ::= SEQUENCE {
                hwSiteCameraIp
                    OCTET STRING,
                hwSiteCameraPort
                    INTEGER,
                hwSiteCameraPhotSetAlarmType
                    INTEGER,
                hwSiteCameraAssociatedAlarmPicture1
                    OCTET STRING,
                hwSiteCameraAssociatedAlarmPicture2
                    OCTET STRING,
                hwSiteCameraAssociatedAlarmPicture3
                    OCTET STRING,
                hwSiteCameraAssociatedAlarmPicture4
                    OCTET STRING,
                hwSiteCameraAssociatedAlarmPicture5
                    OCTET STRING,
                hwSiteCameraAssociatedAlarmPicture6
                    OCTET STRING,
                hwSiteCameraAssociatedAlarmPicture7
                    OCTET STRING,
                hwSiteCameraAssociatedAlarmPicture8
                    OCTET STRING,
                hwSiteCameraAssociatedAlarmPicture9
                    OCTET STRING,
                hwSiteCameraAssociatedAlarmPicture10
                    OCTET STRING,
                hwSiteCameraAdditionalAssociatedAlarmPictures
                    OCTET STRING
            }

        hwSiteCameraIp OBJECT-TYPE
            SYNTAX OCTET STRING
            MAX-ACCESS read-only
            STATUS current
            DESCRIPTION
                "the camera ip adress."
            ::= { hwSiteCameraEntry 1 }

        hwSiteCameraPort OBJECT-TYPE
            SYNTAX INTEGER
                {
                nim1com1(1),
                nim1com2(2),
                nim2com1(3),
                nim2com2(4)
                }
            MAX-ACCESS read-only
            STATUS current
            DESCRIPTION
                "camera connect port number."
            ::= { hwSiteCameraEntry 2 }

        hwSiteCameraPhotSetAlarmType OBJECT-TYPE
            SYNTAX INTEGER
                {
                dooralarm(1),
                smokealarm(2),
                wateralarm(3),
                motiondetectalarm(4)
                }
            MAX-ACCESS read-write
            STATUS current
            DESCRIPTION
                "You can set the alarm type to obtain the historical picture of the camera-related alarm shooting."
            ::= { hwSiteCameraEntry 5 }

        hwSiteCameraAssociatedAlarmPicture1 OBJECT-TYPE
            SYNTAX OCTET STRING
            MAX-ACCESS read-only
            STATUS current
            DESCRIPTION
                "Associated alarm picture 1."
            ::= { hwSiteCameraEntry 6 }

        hwSiteCameraAssociatedAlarmPicture2 OBJECT-TYPE
            SYNTAX OCTET STRING
            MAX-ACCESS read-only
            STATUS current
            DESCRIPTION
                "Associated alarm picture 2."
            ::= { hwSiteCameraEntry 7 }

        hwSiteCameraAssociatedAlarmPicture3 OBJECT-TYPE
            SYNTAX OCTET STRING
            MAX-ACCESS read-only
            STATUS current
            DESCRIPTION
                "Associated alarm picture 3."
            ::= { hwSiteCameraEntry 8 }

        hwSiteCameraAssociatedAlarmPicture4 OBJECT-TYPE
            SYNTAX OCTET STRING
            MAX-ACCESS read-only
            STATUS current
            DESCRIPTION
                "Associated alarm picture 4."
            ::= { hwSiteCameraEntry 9 }

        hwSiteCameraAssociatedAlarmPicture5 OBJECT-TYPE
            SYNTAX OCTET STRING
            MAX-ACCESS read-only
            STATUS current
            DESCRIPTION
                "Associated alarm picture 5."
            ::= { hwSiteCameraEntry 10 }

        hwSiteCameraAssociatedAlarmPicture6 OBJECT-TYPE
            SYNTAX OCTET STRING
            MAX-ACCESS read-only
            STATUS current
            DESCRIPTION
                "Associated alarm picture 6."
            ::= { hwSiteCameraEntry 11 }

        hwSiteCameraAssociatedAlarmPicture7 OBJECT-TYPE
            SYNTAX OCTET STRING
            MAX-ACCESS read-only
            STATUS current
            DESCRIPTION
                "Associated alarm picture 7."
            ::= { hwSiteCameraEntry 12 }

        hwSiteCameraAssociatedAlarmPicture8 OBJECT-TYPE
            SYNTAX OCTET STRING
            MAX-ACCESS read-only
            STATUS current
            DESCRIPTION
                "Associated alarm picture 8."
            ::= { hwSiteCameraEntry 13 }

        hwSiteCameraAssociatedAlarmPicture9 OBJECT-TYPE
            SYNTAX OCTET STRING
            MAX-ACCESS read-only
            STATUS current
            DESCRIPTION
                "Associated alarm picture 9."
            ::= { hwSiteCameraEntry 14 }

        hwSiteCameraAssociatedAlarmPicture10 OBJECT-TYPE
            SYNTAX OCTET STRING
            MAX-ACCESS read-only
            STATUS current
            DESCRIPTION
                "Associated alarm picture 10."
            ::= { hwSiteCameraEntry 15 }

        hwSiteCameraAdditionalAssociatedAlarmPictures OBJECT-TYPE
            SYNTAX OCTET STRING
            MAX-ACCESS read-only
            STATUS current
            DESCRIPTION
                "Additional associated alarm pictures."
            ::= { hwSiteCameraEntry 16 }

END
